BAYOUR-COM-MIB DEFINITIONS ::= BEGIN
-- $Id: BAYOUR-COM-MIB.txt,v 1.20 2011-02-10 16:18:17 turbo Exp $

-- This is my very first MIB! A lot of it is taken from the IF-MIB
-- by the IETF Interfaces MIB Working Group (200006140000).

-- {{{ Imports
IMPORTS
  MODULE-IDENTITY, OBJECT-TYPE, Integer32, Counter32, enterprises FROM SNMPv2-SMI
  MODULE-COMPLIANCE, OBJECT-GROUP                                 FROM SNMPv2-CONF
  TEXTUAL-CONVENTION, DisplayString                               FROM SNMPv2-TC;
-- }}}

-- {{{ bayourCom Module identity
bayourCom MODULE-IDENTITY
  LAST-UPDATED                         "201507121641Z"  -- July 12, 2015
  ORGANIZATION                         "Bayour.COM"
  CONTACT-INFO                         "Postal:      Turbo Fredriksson
                                                     Dobelnsgatan 69
                                                     506 37 Boras
                                                     Sweden

                                        Tel:         +46 704-697645
                                        E-Mail:      turbo@bayour.com"
  DESCRIPTION                          "The MIB module defines the Bayour.COM Bind9, Bacula and ZFS statistics."

  REVISION                             "201507121641Z"  -- July 12, 2015
  DESCRIPTION                          "Add the large int values from draft-perkins-bigint-00."

  REVISION                             "201507121618Z"  -- July 12, 2015
  DESCRIPTION                          "Add support for ARC status values l2_{size,asize} in the zfsARCStatsTable."

  REVISION                             "201507112036Z"  -- July 11, 2015
  DESCRIPTION                          "Support retreiving and printing the pool GUID in the zfsPoolStatusTable."

  REVISION                             "201507082035Z"  -- July 08, 2015
  DESCRIPTION                          "Change the zfsDbufL2Comp from a Integer32 to a ZFSDbufL2CompValue."

  REVISION                             "201409170211Z"  -- September 17, 2014
  DESCRIPTION                          "Added ZFS DBUF status information."

  REVISION                             "201409082041Z"  -- September 8, 2014
  DESCRIPTION                          "Added ZPOOL device status information."

  REVISION                             "201409070242Z"  -- September 7, 2014
  DESCRIPTION                          "Added ZIL information."

  REVISION                             "201407200200Z"  -- July 10, 2014
  DESCRIPTION                          "Added ARC, VFS IOPS and Bandwidth tables."

  REVISION                             "201407191500Z"  -- July 19, 2014
  DESCRIPTION                          "Added ZFS stats."

  REVISION                             "201407191450Z"  -- July 19, 2014
  DESCRIPTION                          "* The Status, Level and VolumeStatus textual conventions needs to be prefixed with 'Bacula'
                                          to make sure it's unique.
                                        * Add the qmailConformance between the bind9 and bacula conformance definitions.
                                          + Renumber the conformances that follows."

  REVISION                             "201102101642Z"  -- February 10, 2011
  DESCRIPTION                          "Updated postal address."

  REVISION                             "200807161802Z"  -- July 16, 2008
  DESCRIPTION                          "Additional columns in the b9stDomainsTable: b9stCounterDuplicate
                                        and b9stCounterDropped."

  REVISION                             "200602230927Z"  -- February 23, 2006
  DESCRIPTION                          "Additional column in the b9stDomainsTable: b9stCounterView."

  REVISION                             "200602051008Z"  -- February 5, 2006
  DESCRIPTION                          "* Add the packageStats information and conformance stuff.
                                        * Add some more folding tags.
                                        * Correct the folding tags informational OID numbers."

  REVISION                             "200510311440Z"  -- October 31, 2005
  DESCRIPTION                          "Change all Counter32's in baculaStats to Integer32's. I've missunderstood
                                        the meaning of Counters's!"

  REVISION                             "200510280655Z"  -- October 28, 2005
  DESCRIPTION                          "* Change all Counter32's in the b9st{Totals,Domains}Table's to Integer32's.
                                          I've missunderstood the meaning of Counters's!
                                        * Add systemStats (and corresponding systemConformance) branch where some
                                          misc system statistics will end up.
                                          This will be (for starters) uptime, memory/swap information and CPU load."

  REVISION                             "200510211259Z"  -- October 21, 2005 - 12:59
  DESCRIPTION                          "* Add a new table containing the counter names - baculaStatsCountersTable.
                                        * The CounterIndex MUST have a range - 0..2147483647 (a full Integer32)."

  REVISION                             "200510201556Z"  -- October 20, 2005 - 15:56
  DESCRIPTION                          "* Change back all Counter64 to Counter32 - can't use Counter64 in a
                                          pass-through scripts because of SMIv1 specification(s)!
                                        * Remove the JobType - missread the SQL table. It's actually a string.
                                        * Remove the baculaStatsCounter. AGAIN. It STILL fucks up the table.
                                          I just don't know why I keep adding it!!"

  REVISION                             "200510191032Z"  -- October 19, 2005 - 10:32
  DESCRIPTION                          "* Job Bytes and Pool Retention, Duration and Bytes and also the Media
                                          writes must be Counter64 because of the size of the value(s).
                                        * Tree missing columns in the Media table added: baculaMediaPool,
                                          baculaMediaType and baculaMediaLabelDate."

  REVISION                             "200510141115Z"  -- October 14, 2005 - 11:15
  DESCRIPTION                          "Missing 'baculaClientCounter' column in the 'BaculaClientsTable' added."

  REVISION                             "200510132053Z"  -- October 13, 2005 - 20:53
  DESCRIPTION                          "* Remove the 0..255 size for DisplayString - it's the default value anyway.
                                        * Rewrite the bacula{Clients,Stats}Table again. Let's see if we can get it
                                          to work this time around...
                                          - The clients table does now ONLY contain information about the client
                                          - A couple on new columns in the stats table
                                        * Add the baculaPools and baculaMedia tables (with 20 and 26 columns respectivly)
                                          with information (writable) about the pools and media library in Bacula.
                                          - Create some textual conventions that ease the setup of some of the Pools
                                            and Media table columns.
                                          - Add baculaGroupPools and baculaGroupMedia used for these two new tables.
                                          - Add two new counters for these tables - baculaTotalPools and baculaTotalMedia.
                                        * Change all entry sequences; put the word 'Entry' right after the table base
                                          instead of at the end - 'B9stEntryTotals' to 'B9stTotalsEntry' makes it
                                          follow the table name ('b9stTotalsTable'). Recomended by SMIv2."

  REVISION                             "200510120724Z"  -- October 12, 2005 - 07:24
  DESCRIPTION                          "* Add folding tags (for/in Emacs) to ease readability.
                                        * Include the TimeStamp text convention from SNMPv2-TC and change the
                                          baculaDate{Start,End} to that instead of DisplayString.
                                        * Move the conformance branch to .0 instead of .10. Might need the room
                                          above 'baculaStats' (.3).
                                        * Make sure all the indexes have access 'not-accessible' instead of
                                          'read-only' - the're indexes.
                                        * Rename the 'baculaClientsTotals' branch to 'baculaTotalClients'.
                                        * Put back 'baculaTotalTypes' and 'baculaTotalStats' which was removed
                                          at a previous commit. Need it after all.
                                        * Modify the description of the 'baculaTotalClients' slightly.
                                        * Instead of ONE table, put the Bacula statistics in two, 'linked' tables.
                                          The new table is: 'baculaStatsTable' which contain the actuall statistic
                                          counters previosly found in the 'baculaClientsTable' table. That table
                                          now only contain the client name(s) and job name(s)."

  REVISION                             "200510061645Z" -- October 6, 2005 - 16:45
  DESCRIPTION                          "Subdivide the 'conformance' branch (branch between that and
                                        'b9st{Compliance,Groups}'; same for the bacula conformance."

  REVISION                             "200510051348Z" -- October 5, 2005 - 13:48
  DESCRIPTION                          "Added the bacula statistics definitions."

  REVISION                             "200504011437Z" -- April 1, 2005 - 14:37
  DESCRIPTION                          "Changed recursive to recursion;
                                        Changed failed to failure;
                                        This according to original Bind9 definitions."

  REVISION                             "200504010000Z" -- April 1, 2005
  DESCRIPTION                          "Initial 'release'."
  ::= { enterprises 8767 }

  snmp                                 OBJECT IDENTIFIER ::= { bayourCom 2 }
-- }}}

-- {{{ Textual conventions
    -- {{{ CounterIndex
    CounterIndex                       ::= TEXTUAL-CONVENTION
      DISPLAY-HINT                     "d"
      STATUS                           current
      DESCRIPTION                      "A unique value, greater than zero, for each type of
                                        counter in the managed system. It is recommended that
                                        values are assigned contiguously starting from 1.
                                        The value for each counter sub-layer must remain
                                        constant at least from one re-initialization of the
                                        entity's network management system to the next
                                        re-initialization."
      SYNTAX                            Integer32 (0..2147483647)
-- }}}

    -- {{{ TrueFalse
    TrueFalse                          ::= TEXTUAL-CONVENTION
      STATUS                           current
      DESCRIPTION                      "True or False values:
                                          false - 0
                                          true  - 1"
      SYNTAX                           INTEGER {
                                         false(0),
                                         true(1)
                                       }
-- }}}

    -- {{{ Bacula Job Status
    BaculaJobStatus                    ::= TEXTUAL-CONVENTION
      STATUS                           current
      DESCRIPTION                      "Job status values:
                                          a - 
                                          r - 
                                          t - 
                                          f - "
      SYNTAX                           INTEGER {
                                         a(1),
                                         r(2),
                                         t(3),
                                         f(4)
                                       }
-- }}}

    -- {{{ Bacula Job Level
    BaculaJobLevel                     ::= TEXTUAL-CONVENTION
      STATUS                           current
      DESCRIPTION                      "Job level values:
                                          d - 
                                          f - Full backup
                                          i - Incremental backup"
      SYNTAX                           INTEGER {
                                         d(0),
                                         f(2),
                                         i(3)
                                       }
-- }}}

    -- {{{ Bacula Volume Status
    BaculaVolumeStatus                 ::= TEXTUAL-CONVENTION
      STATUS                           current
      DESCRIPTION                      "Volume status values:
                                          Full        - 
                                          Archive     - 
                                          Append      - 
                                          Recycle     - 
                                          Purged      - 
                                          Read-Only   - 
                                          Disabled    - 
                                          Error       - 
                                          Busy        - 
                                          Used        - 
                                          Cleaning    - "
      SYNTAX                           INTEGER {
                                         full(1),
                                         archive(2),
                                         append(3),
                                         recycle(4),
                                         purged(5),
                                         readonly(6),
                                         disabled(7),
                                         error(8),
                                         busy(9),
                                         used(10),
                                         cleaning(11)
                                       }
-- }}}

    -- {{{ ZFSPoolStatusValue
    ZFSPoolStatusValue                 ::= TEXTUAL-CONVENTION
      STATUS                           current
      DESCRIPTION                      "ZFS Pool status values:
                                          Degraded - One or more top-level vdevs is in the degraded state because one or more component devices are offline.
                                          Faulted  - One or more top-level vdevs is in the faulted state because one or more component devices are offline.
                                          Offline  - The device was explicitly taken offline by the zpool offline command.
                                          Online   - The device is online and functioning.
                                          Removed  - The device was physically removed while the system was running.
                                          Unavail  - The device could not be opened."
      SYNTAX                           INTEGER {
                                          degraded(1),
                                          faulted(2),
                                          offline(3),
                                          online(4),
                                          removed(5),
                                          unavail(6)
                                       }
-- }}}

    -- {{{ ZFSDbufTypeValue
    ZFSDbufTypeValue                   ::= TEXTUAL-CONVENTION
      STATUS                           current
      DESCRIPTION                      "ZFS DBUF btype and dtype status values:
                                          DMU_OT_NONE
                                          # General:
                                          DMU_OT_OBJECT_DIRECTORY
                                          DMU_OT_OBJECT_ARRAY
                                          DMU_OT_PACKED_NVLIST
                                          DMU_OT_PACKED_NVLIST_SIZE
                                          DMU_OT_BPOBJ
                                          DMU_OT_BPOBJ_HDR
                                          # SPA:
                                          DMU_OT_SPACE_MAP_HEADER
                                          DMU_OT_SPACE_MAP
                                          # ZIL:
                                          DMU_OT_INTENT_LOG
                                          # DMU:
                                          DMU_OT_DNODE
                                          DMU_OT_OBJSET
                                          # DSL:
                                          DMU_OT_DSL_DIR
                                          DMU_OT_DSL_DIR_CHILD_MAP
                                          DMU_OT_DSL_DS_SNAP_MAP
                                          DMU_OT_DSL_PROPS
                                          DMU_OT_DSL_DATASET
                                          # ZPL:
                                          DMU_OT_ZNODE
                                          DMU_OT_OLDACL
                                          DMU_OT_PLAIN_FILE_CONTENTS
                                          DMU_OT_DIRECTORY_CONTENTS
                                          DMU_OT_MASTER_NODE
                                          DMU_OT_UNLINKED_SET
                                          # ZVOL:
                                          DMU_OT_ZVOL
                                          DMU_OT_ZVOL_PROP
                                          # other; for testing only!
                                          DMU_OT_PLAIN_OTHER
                                          DMU_OT_UINT64_OTHER
                                          DMU_OT_ZAP_OTHER
                                          # New object types:
                                          DMU_OT_ERROR_LOG
                                          DMU_OT_SPA_HISTORY
                                          DMU_OT_SPA_HISTORY_OFFSETS
                                          DMU_OT_POOL_PROPS
                                          DMU_OT_DSL_PERMS
                                          DMU_OT_ACL
                                          DMU_OT_SYSACL
                                          DMU_OT_FUID
                                          DMU_OT_FUID_SIZE
                                          DMU_OT_NEXT_CLONES
                                          DMU_OT_SCAN_QUEUE
                                          DMU_OT_USERGROUP_USED
                                          DMU_OT_USERGROUP_QUOTA
                                          DMU_OT_USERREFS
                                          DMU_OT_DDT_ZAP
                                          DMU_OT_DDT_STATS
                                          DMU_OT_SA
                                          DMU_OT_SA_MASTER_NODE
                                          DMU_OT_SA_ATTR_REGISTRATION
                                          DMU_OT_SA_ATTR_LAYOUTS
                                          DMU_OT_SCAN_XLATE
                                          DMU_OT_DEDUP
                                          DMU_OT_DEADLIST
                                          DMU_OT_DEADLIST_HDR
                                          DMU_OT_DSL_CLONES
                                          DMU_OT_BPOBJ_SUBOBJ
                                          UNKNOWN (196)"
      SYNTAX                           INTEGER {
                                          none(0),
                                          objectdirectory(1),
                                          objectarray(2),
                                          packednvlist(3),
                                          packednvlistsize(4),
                                          bpobj(5),
                                          bpobjhdr(6),
                                          spacemapheader(7),
                                          spacemap(8),
                                          intentlog(9),
                                          dnode(10),
                                          objset(11),
                                          dsldir(12),
                                          dsldirchildmap(13),
                                          dsldssnapmap(14),
                                          dslprops(15),
                                          dsldataset(16),
                                          znode(17),
                                          oldacl(18),
                                          plainfilecontents(19),
                                          directorycontents(20),
                                          masternode(21),
                                          unlinkedset(22),
                                          zvol(23),
                                          zvolprop(24),
                                          plainother(25),
                                          uint64other(26),
                                          zapother(27),
                                          errorlog(28),
                                          spahistory(29),
                                          spahistoryoffsets(30),
                                          poolprops(31),
                                          dslperms(32),
                                          acl(33),
                                          sysacl(34),
                                          fuid(35),
                                          fuidsize(36),
                                          nextclones(37),
                                          scanqueue(38),
                                          usergroupused(39),
                                          usergroupquota(40),
                                          userrefs(41),
                                          ddtzap(42),
                                          ddtstats(43),
                                          sa(44),
                                          samasternode(45),
                                          saattrregistration(46),
                                          saattrlayouts(47),
                                          scanxlate(48),
                                          dedup(49),
                                          deadlist(50),
                                          deadlisthdr(51),
                                          dslclones(52),
                                          bpobjsubobj(53),
                                          unknown(196)
                                       }
-- }}}

    -- {{{ ZFSDbufL2CompValue
    ZFSDbufL2CompValue                 ::= TEXTUAL-CONVENTION
      STATUS                           current
      DESCRIPTION                      "ZFS DBUF l2_comp status values:
                                          ZIO_COMPRESS_INHERIT
                                          ZIO_COMPRESS_ON
                                          ZIO_COMPRESS_OFF
                                          ZIO_COMPRESS_LZJB
                                          ZIO_COMPRESS_EMPTY
                                          ZIO_COMPRESS_GZIP_1
                                          ZIO_COMPRESS_GZIP_2
                                          ZIO_COMPRESS_GZIP_3
                                          ZIO_COMPRESS_GZIP_4
                                          ZIO_COMPRESS_GZIP_5
                                          ZIO_COMPRESS_GZIP_6
                                          ZIO_COMPRESS_GZIP_7
                                          ZIO_COMPRESS_GZIP_8
                                          ZIO_COMPRESS_GZIP_9
                                          ZIO_COMPRESS_ZLE
                                          ZIO_COMPRESS_LZ4
                                          ZIO_COMPRESS_FUNCTION"
      SYNTAX                           INTEGER {
                                          inherit(0),
                                          on(1),
                                          off(2),
                                          lzjb(3),
                                          empty(4),
                                          gzip1(5),
                                          gzip2(6),
                                          gzip3(7),
                                          gzip4(8),
                                          gzip5(9),
                                          gzip6(10),
                                          gzip7(11),
                                          gzip8(12),
                                          gzip9(13),
                                          zle(14),
                                          lz4(15),
                                          function(16)
                                       }
-- }}}
-- }}}

    -- {{{ .1.3.6.1.4.1.8767.2.0 conformance
    conformance                        OBJECT IDENTIFIER ::= { snmp 0 }
      -- {{{ .1.3.6.1.4.1.8767.2.0.1 bind9Conformance
      bind9Conformance                 OBJECT IDENTIFIER ::= { conformance 1 }
        -- {{{ .1.3.6.1.4.1.8767.2.0.1.1 b9stCompliance
        b9stCompliance                 MODULE-COMPLIANCE
          STATUS                       current
          DESCRIPTION                  "The compliance statement for SNMP entities which have
                                        bind9 status counters."
          MODULE  -- this module
          MANDATORY-GROUPS             { b9stGroupTotals, b9stGroupDomains }
          ::= { bind9Conformance 1 }
-- }}}

        -- {{{ .1.3.6.1.4.1.8767.2.0.1.2 b9stGroups
        b9stGroups                     OBJECT IDENTIFIER ::= { bind9Conformance 2 }
          b9stGroupTotals              OBJECT-GROUP
            OBJECTS                    { b9stNumberTotals, b9stCounterName, b9stCounterTotal,
                                         b9stCounterForward, b9stCounterReverse }
            STATUS                     current
            DESCRIPTION                "A collection of objects providing information
                                        applicable to B9st statistics."
            ::= { b9stGroups 1 }

          b9stGroupDomains             OBJECT-GROUP
            OBJECTS                    { b9stNumberDomains, b9stDomainName, b9stCounterSuccess,
                                         b9stCounterReferral, b9stCounterNXRRSet, b9stCounterNXDomain,
                                         b9stCounterRecursion, b9stCounterFailure, b9stCounterDuplicate,
                                         b9stCounterDropped, b9stCounterView }
            STATUS                     current
            DESCRIPTION                "A collection of objects providing information
                                        applicable to B9st statistics."
            ::= { b9stGroups 2 }
-- }}}
-- }}}

      -- {{{ .1.3.6.1.4.1.8767.2.0.2 qmailConformance
      qmailConformance                 OBJECT IDENTIFIER ::= { conformance 2 }
-- }}}

      -- {{{ .1.3.6.1.4.1.8767.2.0.3 baculaConformance
      baculaConformance                OBJECT IDENTIFIER ::= { conformance 3 }
        -- {{{ .1.3.6.1.4.1.8767.2.0.3.1 baculaCompliance
        baculaCompliance               MODULE-COMPLIANCE
          STATUS                       current
          DESCRIPTION                  "The compliance statement for SNMP entities which have
                                        bacula status counters."
          MODULE                       -- this module
          MANDATORY-GROUPS             { baculaGroupClients, baculaGroupJobNames, baculaGroupJobIDs,
                                         baculaGroupCounters, baculaGroupStats, baculaGroupPools,
                                         baculaGroupMedia }
          ::= { baculaConformance 1 }
-- }}}

        -- {{{ .1.3.6.1.4.1.8767.2.0.3.2 baculaGroups
        baculaGroups                   OBJECT IDENTIFIER ::= { baculaConformance 3 }
          baculaGroupClients           OBJECT-GROUP
            OBJECTS                    { baculaTotalClients, baculaClientName, baculaClientUname,
                                         baculaClientAutoPrune, baculaClientRetentionFile,
                                         baculaClientRetentionJob }
            STATUS                     current
            DESCRIPTION                "A collection of objects providing information
                                        applicable to Bacula statistics."
            ::= { baculaGroups 1 }

          baculaGroupJobNames          OBJECT-GROUP
            OBJECTS                    { baculaJobsName, baculaJobsDesc, baculaJobsMD5, baculaJobsCreate }
            STATUS                     current
            DESCRIPTION                "A collection of objects providing information
                                        applicable to Bacula statistics."
            ::= { baculaGroups 2 }

          baculaGroupJobIDs            OBJECT-GROUP
            OBJECTS                    { baculaJobsID }
            STATUS                     current
            DESCRIPTION                "A collection of objects providing information
                                        applicable to Bacula statistics."
            ::= { baculaGroups 3 }

          baculaGroupCounters          OBJECT-GROUP
            OBJECTS                    { baculaStatsCounterName }
            STATUS                     current
            DESCRIPTION                "A collection of objects providing information
                                        applicable to Bacula statistics."
            ::= { baculaGroups 4 }


          baculaGroupStats             OBJECT-GROUP
            OBJECTS                    { baculaTotalStats, baculaStatsStart, baculaStatsEnd,
                                         baculaStatsDuration, baculaStatsFiles, baculaStatsBytes,
                                         baculaStatsType, baculaStatsStatus, baculaStatsLevel,
                                         baculaStatsErrors, baculaStatsMissingFiles }
            STATUS                     current
            DESCRIPTION                "A collection of objects providing information
                                        applicable to Bacula statistics."
            ::= { baculaGroups 5 }

          baculaGroupPools             OBJECT-GROUP
            OBJECTS                    { baculaTotalPools, baculaPoolsName, baculaPoolsNum,
                                         baculaPoolsMax, baculaPoolsUseOnce, baculaPoolsUseCatalog,
                                         baculaPoolsAcceptAnyVolume, baculaPoolsRetention,
                                         baculaPoolsDuration, baculaPoolsMaxJobs, baculaPoolsMaxFiles,
                                         baculaPoolsMaxBytes, baculaPoolsAutoPrune, baculaPoolsRecycle,
                                         baculaPoolsType, baculaPoolsLabelFormat, baculaPoolsEnabled,
                                         baculaPoolsScratchPoolID, baculaPoolsRecyclePoolID }
            STATUS                     current
            DESCRIPTION                "A collection of objects providing information
                                        applicable to Bacula statistics."
            ::= { baculaGroups 6 }

          baculaGroupMedia             OBJECT-GROUP
            OBJECTS                    { baculaTotalMedia, baculaMediaName, baculaMediaSlot,
                                         baculaMediaPool, baculaMediaType, baculaMediaWrittenFirst,
                                         baculaMediaWrittenLast, baculaMediaLabelDate, baculaMediaJobs,
                                         baculaMediaFiles, baculaMediaBlocks, baculaMediaMounts,
                                         baculaMediaBytes, baculaMediaErrors, baculaMediaWrites,
                                         baculaMediaCapacity, baculaMediaStatus, baculaMediaRecycle,
                                         baculaMediaRetention, baculaMediaDuration, baculaMediaMaxJobs,
                                         baculaMediaMaxFiles, baculaMediaMaxBytes, baculaMediaInChanger,
                                         baculaMediaMediaAddressing, baculaMediaReadTime, baculaMediaWriteTime,
                                         baculaMediaEndFile, baculaMediaEndBlock }
            STATUS                     current
            DESCRIPTION                "A collection of objects providing information
                                        applicable to Bacula statistics."
            ::= { baculaGroups 7 }
-- }}}
-- }}}

      -- {{{ .1.3.6.1.4.1.8767.2.0.4 systemConformance
      systemConformance                OBJECT IDENTIFIER ::= { conformance 4 }
        -- {{{ .1.3.6.1.4.1.8767.2.0.4.1 systemCompliance
        systemCompliance               MODULE-COMPLIANCE
          STATUS                       current
          DESCRIPTION                  "The compliance statement for SNMP entities which have
                                        system status counters."
          MODULE                       -- this module
          MANDATORY-GROUPS             { systemGroupMemory, systemGroupCPU, systemGroupLoad,
                                         systemGroupMisc }
          ::= { systemConformance 1 }
-- }}}

        -- {{{ .1.3.6.1.4.1.8767.2.0.3.2 systemgroups
        systemGroups                   OBJECT IDENTIFIER ::= { systemConformance 2 }
          systemGroupMemory            OBJECT-GROUP
            OBJECTS                    { systemMemoryTotal, systemMemoryUsed, systemMemoryFree,
                                         systemMemoryBuffered, systemMemoryCached, systemMemorySwapTotal,
                                         systemMemorySwapUsed, systemMemorySwapFree }
            STATUS                     current
            DESCRIPTION                "A collection of objects providing information
                                        applicable to System memory statistics."
            ::= { systemGroups 1 }

          systemGroupCPU               OBJECT-GROUP
            OBJECTS                    { systemCPUTasksTotal, systemCPUTasksRunning, systemCPUTasksSleeping,
                                         systemCPUTasksStopped, systemCPUTasksZombies, systemCPUUsageUser,
                                         systemCPUUsageSystem, systemCPUUsageNice, systemCPUUsageIdle,
                                         systemCPUUsageIOWait }
            STATUS                     current
            DESCRIPTION                "A collection of objects providing information
                                        applicable to System CPU statistics."
            ::= { systemGroups 2 }

          systemGroupLoad              OBJECT-GROUP
            OBJECTS                    { systemLoadLastOne, systemLoadLastFive, systemLoadLastFifteen }
            STATUS                     current
            DESCRIPTION                "A collection of objects providing information
                                        applicable to System load statistics."
            ::= { systemGroups 3 }

          systemGroupMisc              OBJECT-GROUP
            OBJECTS                    { systemUptime }
            STATUS                     current
            DESCRIPTION                "A collection of objects providing information
                                        applicable to misc system statistics."
            ::= { systemGroups 4 }
-- }}}
-- }}}

      -- {{{ .1.3.6.1.4.1.8767.2.0.5 packageConformance
      packageConformance               OBJECT IDENTIFIER ::= { conformance 5 }
        -- {{{ .1.3.6.1.4.1.8767.2.0.5.1 packageCompliance
        packageCompliance              MODULE-COMPLIANCE
          STATUS                       current
          DESCRIPTION                  "The compliance statement for SNMP entities which have
                                        package status information."
          MODULE                       -- this module
          MANDATORY-GROUPS             {  packageStatsGroup, packageInfoGroup }
          ::= { packageConformance 1 }
-- }}}

        -- {{{ .1.3.6.1.4.1.8767.2.0.4.2 packageGroups
        packageGroups                  OBJECT IDENTIFIER ::= { packageConformance 2 }
          packageStatsGroup            OBJECT-GROUP
            OBJECTS                    { packageName, packageVersion, packageDesc, packageStatus }
            STATUS                     current
            DESCRIPTION                "A collection of objects providing information
                                        applicable to Package statistics."
            ::= { packageGroups 1 }

          packageInfoGroup             OBJECT-GROUP
            OBJECTS                    { packagePriority, packageSection, packageMaintainer,
                                         packageSource, packageDepends, packageRecommends,
                                         packageSuggests, packageSize, packageMD5Sum }
            STATUS                     current
            DESCRIPTION                "A collection of objects providing information
                                        applicable to Package information."
            ::= { packageGroups 2 }
-- }}}
-- }}}

      -- {{{ .1.3.6.1.4.1.8767.2.0.6 zfsConformance
      zfsConformance                   OBJECT IDENTIFIER ::= { conformance 6 }
        -- {{{ .1.3.6.1.4.1.8767.2.0.6.1 zfsCompliance
        zfsCompliance                  MODULE-COMPLIANCE
          STATUS                       current
          DESCRIPTION                  "The compliance statement for SNMP entities which have
                                        ZFS status counters."
          MODULE                       -- this module
          MANDATORY-GROUPS             { zfsGroupTotals, zfsGroupStatus, zfsGroupARCUsage,
                                         zfsGroupARCStats, zfsGroupVFSIOPS, zfsGroupVFSBandwith,
                                         zfsGroupZILStats, zfsGroupDevStats, zfsGroupDbufStats }
          ::= { zfsConformance 1 }
-- }}}

        -- {{{ .1.3.6.1.4.1.8767.2.0.6.2 zfsGroups
        zfsGroups                      OBJECT IDENTIFIER ::= { zfsConformance 2 }
          zfsGroupTotals               OBJECT-GROUP
            OBJECTS                    { zfsTotalPools, zfsTotalDatasets, zfsTotalVolumes,
                                       zfsTotalSnapshots }
            STATUS                     current
            DESCRIPTION                "A collection of objects providing information
                                        applicable to ZFS statistics."
            ::= { zfsGroups 1 }

          zfsGroupStatus               OBJECT-GROUP
            OBJECTS                    { zfsPoolName, zfsPoolGUID, zfsPoolSize, zfsPoolAlloc, zfsPoolFree,
                                         zfsPoolCap, zfsPoolDedup, zfsPoolHealth, zfsPoolAltRoot,
                                         zfsPoolUsedBySnaps, zfsPoolUsed, zfsOperReads, zfsOperWrites,
                                         zfsBandwidthReads, zfsBandwidthWrites }
            STATUS                     current
            DESCRIPTION                "ZFS Pool status values."
            ::= { zfsGroups 2 }

          zfsGroupARCUsage             OBJECT-GROUP
            OBJECTS                    { zfsARCMetaMax, zfsARCMetaUsed, zfsARCMetaLimit,
                                         zfsARCCMax, zfsARCSize }
                                         
            STATUS                     current
            DESCRIPTION                "ZFS ARC usage values."
            ::= { zfsGroups 3 }

          zfsGroupARCStats             OBJECT-GROUP
            OBJECTS                    { zfsARCHits, zfsARCMisses, zfsARCDemandDataHits,
                                         zfsARCDemandDataMisses, zfsARCDemandMetaHits,
                                         zfsARCDemandMetaMisses, zfsARCPrefetchDataHits,
                                         zfsARCPrefetchDataMisses, zfsARCPrefetchMetaHits,
                                         zfsARCPrefetchMetaMisses, zfsARCL2Size, zfsARCL2ASize,
                                         zfsARCL2Hits, zfsARCL2Misses }
            STATUS                     current
            DESCRIPTION                "ZFS ARC status values."
            ::= { zfsGroups 4 }

          zfsGroupVFSIOPS              OBJECT-GROUP
            OBJECTS                    { zfsPoolName, zfsOperReads, zfsOperWrites }
            STATUS                     current
            DESCRIPTION                "ZFS VFS IOPS status values."
            ::= { zfsGroups 5 }

          zfsGroupVFSBandwith          OBJECT-GROUP
            OBJECTS                    { zfsPoolName, zfsBandwidthReads, zfsBandwidthWrites }
            STATUS                     current
            DESCRIPTION                "ZFS VFS Bandwidth status values."
            ::= { zfsGroups 6 }

          zfsGroupZILStats             OBJECT-GROUP
            OBJECTS                    { zfsZILCommitCnt, zfsZILCommitWriterCnt, zfsZILITXCnt,
                                         zfsZILITXIndirectCnt, zfsZILITXIndirectBytes, zfsZILITXCopiedCnt,
                                         zfsZILITXCopiedBytes, zfsZILITXNeedcopyCnt, zfsZILITXNeedcopyBytes,
                                         zfsZILITXMetaslabNormalCnt, zfsZILITXMetaslabNormalBytes,
                                         zfsZILITXMetaslabSLOGCnt, zfsZILITXMetaslabSLOGBytes }
            STATUS                     current
            DESCRIPTION                "ZFS ZIL status values."
            ::= { zfsGroups 7 }

          zfsGroupDevStats             OBJECT-GROUP
            OBJECTS                    { zfsPoolDevName, zfsPoolDevState, zfsPoolDevRead, 
                                         zfsPoolDevWrite, zfsPoolDevCksum }
            STATUS                     current
            DESCRIPTION                "ZFS device status values."
            ::= { zfsGroups 8 }

          zfsGroupDbufStats            OBJECT-GROUP
            OBJECTS                    { zfsDbufPoolName, zfsDbufObjSet, zfsDbufObject,
                                         zfsDbufLevel, zfsDbufBlkId, zfsDbufOffset,
                                         zfsDbufDBSize, zfsDbufMeta, zfsDbufState,
                                         zfsDbufDBHolds, zfsDbufList, zfsDbufAType,
                                         zfsDbufIndex, zfsDbufFlags, zfsDbufCount,
                                         zfsDbufASize, zfsDbufAccess, zfsDbufMRU,
                                         zfsDbufGMRU, zfsDbufMFU, zfsDbufGMFU, zfsDbufL2,
                                         zfsDbufL2DAttr, zfsDbufL2ASize, zfsDbufL2Comp,
                                         zfsDbufAHolds, zfsDbufDType, zfsDbufBType,
                                         zfsDbufDataBS, zfsDbufMetaBS, zfsDbufBSize,
                                         zfsDbufLvls, zfsDbufDHolds, zfsDbufBlocks,
                                         zfsDbufDSize }
            STATUS                     current
            DESCRIPTION                "ZFS dbuf status values."
            ::= { zfsGroups 9 }
-- }}}
-- }}}
-- }}}

    -- {{{ .1.3.6.1.4.1.8767.2.1 bind9Stats
    bind9Stats                         OBJECT IDENTIFIER ::= { snmp 1 }
      -- {{{ .1.3.6.1.4.1.8767.2.1.x b9stNumber{Totals,Domains}
      b9stNumberTotals                 OBJECT-TYPE
        SYNTAX                         Integer32
        MAX-ACCESS                     read-only
        STATUS                         current
        DESCRIPTION                    "Number of Bind9 status counters"
        ::= { bind9Stats 1 }
  
      b9stNumberDomains                OBJECT-TYPE
        SYNTAX                         Integer32
        MAX-ACCESS                     read-only
        STATUS                         current
        DESCRIPTION                    "Number of Bind9 status counters"
        ::= { bind9Stats 2 }
-- }}}
  
      -- {{{ .1.3.6.1.4.1.8767.2.1.3 b9stTotalsTable
      b9stTotalsTable                  OBJECT-TYPE
        SYNTAX                         SEQUENCE OF B9stTotalsEntry
        MAX-ACCESS                     not-accessible
        STATUS                         current
        DESCRIPTION                    "A list of Bind9 statistic counters (totals)."
        ::= { bind9Stats 3 }
  
        b9stTotalsEntry                OBJECT-TYPE
          SYNTAX                       B9stTotalsEntry
          MAX-ACCESS                   not-accessible
          STATUS                       current
          DESCRIPTION                  "An entry containing Bind9 statistics (totals)."
          INDEX                        { b9stIndexTotals }
          ::= { b9stTotalsTable 1 }
  
          B9stTotalsEntry              ::= SEQUENCE {
            b9stIndexTotals            CounterIndex,

            b9stCounterName            DisplayString,
            b9stCounterTotal           Integer32,
            b9stCounterForward         Integer32,
            b9stCounterReverse         Integer32
          }
  
          b9stIndexTotals              OBJECT-TYPE
            SYNTAX                     CounterIndex
            MAX-ACCESS                 not-accessible
            STATUS                     current
            DESCRIPTION                "Reference Index for each counter."
            ::= { b9stTotalsEntry 1 }
  
          b9stCounterName              OBJECT-TYPE
            SYNTAX                     DisplayString
            MAX-ACCESS                 read-only
            STATUS                     current
            DESCRIPTION                "A textual string containing information about the
                                        statistics counters. This string should include the
                                        name of the counter."
            ::= { b9stTotalsEntry 2 }

          b9stCounterTotal             OBJECT-TYPE
            SYNTAX                     Integer32
            MAX-ACCESS                 read-only
            STATUS                     current
            DESCRIPTION                "Total number of requests."
            ::= { b9stTotalsEntry 3 }

          b9stCounterForward           OBJECT-TYPE
            SYNTAX                     Integer32
            MAX-ACCESS                 read-only
            STATUS                     current
            DESCRIPTION                "Total number of forward requests."
            ::= { b9stTotalsEntry 4 }

          b9stCounterReverse           OBJECT-TYPE
            SYNTAX                     Integer32
            MAX-ACCESS                 read-only
            STATUS                     current
            DESCRIPTION                "Total number of reverse requests."
            ::= { b9stTotalsEntry 5 }
-- }}}

      -- {{{ .1.3.6.1.4.1.8767.2.1.4 b9stDomainsTable
      b9stDomainsTable                 OBJECT-TYPE
        SYNTAX                         SEQUENCE OF B9stDomainsEntry
        MAX-ACCESS                     not-accessible
        STATUS                         current
        DESCRIPTION                    "A list of Bind9 statistic counters"
        ::= { bind9Stats 4 }
  
        b9stDomainsEntry               OBJECT-TYPE
          SYNTAX                       B9stDomainsEntry
          MAX-ACCESS                   not-accessible
          STATUS                       current
          DESCRIPTION                  "An entry containing Bind9 statistics"
          INDEX                        { b9stIndexDomains }
          ::= { b9stDomainsTable 1 }
  
          B9stDomainsEntry             ::= SEQUENCE {
            b9stIndexDomains           CounterIndex,

            b9stDomainName             DisplayString,
            b9stCounterSuccess         Integer32,
            b9stCounterReferral        Integer32,
            b9stCounterNXRRSet         Integer32,
            b9stCounterNXDomain        Integer32,
            b9stCounterRecursion       Integer32,
            b9stCounterFailure         Integer32,
            b9stCounterDuplicate       Integer32,
            b9stCounterDropped         Integer32,
            b9stCounterView            DisplayString
          }
  
          b9stIndexDomains             OBJECT-TYPE
            SYNTAX                     CounterIndex
            MAX-ACCESS                 not-accessible
            STATUS                     current
            DESCRIPTION                "Reference Index for each counter."
            ::= { b9stDomainsEntry 1 }
  
          b9stDomainName               OBJECT-TYPE
            SYNTAX                     DisplayString
            MAX-ACCESS                 read-only
            STATUS                     current
            DESCRIPTION                "A textual string containing information about the
                                        statistics counters. This string should include the
                                        name of the counter."
            ::= { b9stDomainsEntry 2 }

          b9stCounterSuccess           OBJECT-TYPE
            SYNTAX                     Integer32
            MAX-ACCESS                 read-only
            STATUS                     current
            DESCRIPTION                "Successful requests for this domain."
            ::= { b9stDomainsEntry 3 }

          b9stCounterReferral          OBJECT-TYPE
            SYNTAX                     Integer32
            MAX-ACCESS                 read-only
            STATUS                     current
            DESCRIPTION                "Referral requests for this domain."
            ::= { b9stDomainsEntry 4 }

          b9stCounterNXRRSet           OBJECT-TYPE
            SYNTAX                     Integer32
            MAX-ACCESS                 read-only
            STATUS                     current
            DESCRIPTION                "Total number of NXRRSet responses."
            ::= { b9stDomainsEntry 5 }

          b9stCounterNXDomain          OBJECT-TYPE
            SYNTAX                     Integer32
            MAX-ACCESS                 read-only
            STATUS                     current
            DESCRIPTION                "Total number of NXDomain responses."
            ::= { b9stDomainsEntry 6 }

          b9stCounterRecursion         OBJECT-TYPE
            SYNTAX                     Integer32
            MAX-ACCESS                 read-only
            STATUS                     current
            DESCRIPTION                "Total number of recursive requests."
            ::= { b9stDomainsEntry 7 }

          b9stCounterFailure           OBJECT-TYPE
            SYNTAX                     Integer32
            MAX-ACCESS                 read-only
            STATUS                     current
            DESCRIPTION                "Total number of failed requests."
            ::= { b9stDomainsEntry 8 }

          b9stCounterDuplicate         OBJECT-TYPE
            SYNTAX                     Integer32
            MAX-ACCESS                 read-only
            STATUS                     current
            DESCRIPTION                "Total number of duplicate requests."
            ::= { b9stDomainsEntry 9 }

          b9stCounterDropped           OBJECT-TYPE
            SYNTAX                     Integer32
            MAX-ACCESS                 read-only
            STATUS                     current
            DESCRIPTION                "Total number of dropped requests."
            ::= { b9stDomainsEntry 10 }

          b9stCounterView              OBJECT-TYPE
            SYNTAX                     DisplayString
            MAX-ACCESS                 read-only
            STATUS                     current
            DESCRIPTION                "Bind9 view the domain is located in."
            ::= { b9stDomainsEntry 11 }
-- }}}
-- }}}

    -- {{{ .1.3.6.1.4.1.8767.2.2 qmailStats
    qmailStats                         OBJECT IDENTIFIER ::= { snmp 2 }
-- }}}

    -- {{{ .1.3.6.1.4.1.8767.2.3 baculaStats
    baculaStats                        OBJECT IDENTIFIER ::= { snmp 3 }
      -- {{{ .1.3.6.1.4.1.8767.2.3.x  baculaTotal{Clients,Stats,Pools,Media}
      baculaTotalClients               OBJECT-TYPE
        SYNTAX                         Integer32
        MAX-ACCESS                     read-only
        STATUS                         current
        DESCRIPTION                    "Total number of Bacula clients."
        ::= { baculaStats 1 }

      baculaTotalStats                 OBJECT-TYPE
        SYNTAX                         Integer32
        MAX-ACCESS                     read-only
        STATUS                         current
        DESCRIPTION                    "Total number of Bacula statistics."
        ::= { baculaStats 2 }

      baculaTotalPools                 OBJECT-TYPE
        SYNTAX                         Integer32
        MAX-ACCESS                     read-only
        STATUS                         current
        DESCRIPTION                    "Total number of Bacula pool entries."
        ::= { baculaStats 3 }

      baculaTotalMedia                 OBJECT-TYPE
        SYNTAX                         Integer32
        MAX-ACCESS                     read-only
        STATUS                         current
        DESCRIPTION                    "Total number of Bacula media entries."
        ::= { baculaStats 4 }
-- }}}

      -- {{{ .1.3.6.1.4.1.8767.2.3.5  baculaClientsTable
      baculaClientsTable               OBJECT-TYPE
        SYNTAX                         SEQUENCE OF BaculaClientsEntry
        MAX-ACCESS                     not-accessible
        STATUS                         current
        DESCRIPTION                    "A list of bacula statistic counters"
        ::= { baculaStats 5 }
  
        baculaClientsEntry             OBJECT-TYPE
          SYNTAX                       BaculaClientsEntry
          MAX-ACCESS                   not-accessible
          STATUS                       current
          DESCRIPTION                  "An entry containing bacula statistics"
          INDEX                        { baculaClientsIndex }
          ::= { baculaClientsTable 1 }
  
          BaculaClientsEntry           ::= SEQUENCE {
            baculaClientsIndex         CounterIndex,

            baculaClientName           DisplayString,
            baculaClientUname          DisplayString,
            baculaClientAutoPrune      TrueFalse,
            baculaClientRetentionFile  Integer32,
            baculaClientRetentionJob   Integer32
          }
  
          baculaClientsIndex           OBJECT-TYPE
            SYNTAX                     CounterIndex
            MAX-ACCESS                 not-accessible
            STATUS                     current
            DESCRIPTION                "Reference Index for each counter."
            ::= { baculaClientsEntry 1 }
  
          baculaClientName             OBJECT-TYPE
            SYNTAX                     DisplayString
            MAX-ACCESS                 read-only
            STATUS                     current
            DESCRIPTION                "A textual string containing information about the
                                        statistics counters. This string should include the
                                        name of the counter."
            ::= { baculaClientsEntry 2 }

          baculaClientUname            OBJECT-TYPE
            SYNTAX                     DisplayString
            MAX-ACCESS                 read-only
            STATUS                     current
            DESCRIPTION                "A textual string containing information about the job."
            ::= { baculaClientsEntry 3 }

          baculaClientAutoPrune        OBJECT-TYPE
            SYNTAX                     TrueFalse
            MAX-ACCESS                 read-write
            STATUS                     current
            DESCRIPTION                "A textual string containing information about the job."
            ::= { baculaClientsEntry 4 }

          baculaClientRetentionFile    OBJECT-TYPE
            SYNTAX                     Integer32
            MAX-ACCESS                 read-write
            STATUS                     current
            DESCRIPTION                "A textual string containing information about the job."
            ::= { baculaClientsEntry 5 }

          baculaClientRetentionJob     OBJECT-TYPE
            SYNTAX                     Integer32
            MAX-ACCESS                 read-write
            STATUS                     current
            DESCRIPTION                "A textual string containing information about the job."
            ::= { baculaClientsEntry 6 }

-- }}}

      -- {{{ .1.3.6.1.4.1.8767.2.3.6  baculaJobsNameTable
      baculaJobsNameTable              OBJECT-TYPE
        SYNTAX                         SEQUENCE OF BaculaJobsNameEntry
        MAX-ACCESS                     not-accessible
        STATUS                         current
        DESCRIPTION                    "A list of bacula statistic counters"
        ::= { baculaStats 6 }
  
        baculaJobsNameEntry            OBJECT-TYPE
          SYNTAX                       BaculaJobsNameEntry
          MAX-ACCESS                   not-accessible
          STATUS                       current
          DESCRIPTION                  "An entry containing bacula statistics"
          INDEX                        { baculaClientsIndex, baculaJobsNameIndex }
          ::= { baculaJobsNameTable 1 }
  
          BaculaJobsNameEntry          ::= SEQUENCE {
            baculaJobsNameIndex        CounterIndex,

            baculaJobsName             DisplayString,
            baculaJobsDesc             DisplayString,
            baculaJobsMD5              DisplayString,
            baculaJobsCreate           DisplayString
          }
  
          baculaJobsNameIndex          OBJECT-TYPE
            SYNTAX                     CounterIndex
            MAX-ACCESS                 not-accessible
            STATUS                     current
            DESCRIPTION                "Reference Index for each counter."
            ::= { baculaJobsNameEntry 1 }
  
          baculaJobsName               OBJECT-TYPE
            SYNTAX                     DisplayString
            MAX-ACCESS                 read-only
            STATUS                     current
            DESCRIPTION                "A textual string containing the NAME of the job."
            ::= { baculaJobsNameEntry 2 }

          baculaJobsDesc               OBJECT-TYPE
            SYNTAX                     DisplayString
            MAX-ACCESS                 read-only
            STATUS                     current
            DESCRIPTION                "A textual string containing the DESCRIPTION of the job."
            ::= { baculaJobsNameEntry 3 }

          baculaJobsMD5                OBJECT-TYPE
            SYNTAX                     DisplayString
            MAX-ACCESS                 read-only
            STATUS                     current
            DESCRIPTION                "A textual string containing the MD5 sum of the job."
            ::= { baculaJobsNameEntry 4 }

          baculaJobsCreate             OBJECT-TYPE
            SYNTAX                     DisplayString
            MAX-ACCESS                 read-only
            STATUS                     current
            DESCRIPTION                "A textual string containing the create time of the job."
            ::= { baculaJobsNameEntry 5 }
-- }}}

      -- {{{ .1.3.6.1.4.1.8767.2.3.7  baculaJobsIDTable
      baculaJobsIDTable                OBJECT-TYPE
        SYNTAX                         SEQUENCE OF BaculaJobsIDEntry
        MAX-ACCESS                     not-accessible
        STATUS                         current
        DESCRIPTION                    "A list of bacula statistic counters"
        ::= { baculaStats 7 }
  
        baculaJobsIDEntry              OBJECT-TYPE
          SYNTAX                       BaculaJobsIDEntry
          MAX-ACCESS                   not-accessible
          STATUS                       current
          DESCRIPTION                  "An entry containing bacula statistics"
          INDEX                        { baculaClientsIndex, baculaJobsNameIndex, baculaJobsIDIndex }
          ::= { baculaJobsIDTable 1 }
  
          BaculaJobsIDEntry            ::= SEQUENCE {
            baculaJobsIDIndex          CounterIndex,

            baculaJobsID               DisplayString
          }
  
          baculaJobsIDIndex            OBJECT-TYPE
            SYNTAX                     CounterIndex
            MAX-ACCESS                 not-accessible
            STATUS                     current
            DESCRIPTION                "Reference Index for each counter."
            ::= { baculaJobsIDEntry 1 }
  
          baculaJobsID                 OBJECT-TYPE
            SYNTAX                     DisplayString
            MAX-ACCESS                 read-only
            STATUS                     current
            DESCRIPTION                "A textual string containing the ID of the job."
            ::= { baculaJobsIDEntry 2 }
-- }}}

      -- {{{ .1.3.6.1.4.1.8767.2.3.8  baculaStatsCountersTable
      baculaStatsCountersTable        OBJECT-TYPE
        SYNTAX                        SEQUENCE OF BaculaStatsCountersEntry
        MAX-ACCESS                    not-accessible
        STATUS                        current
        DESCRIPTION                   "A list of bacula statistic counter names."
        ::= { baculaStats 8 }

        baculaStatsCountersEntry        OBJECT-TYPE
          SYNTAX                        BaculaStatsCountersEntry
          MAX-ACCESS                    not-accessible
          STATUS                        current
          DESCRIPTION                   "An entry containing bacula statistic counter names."
          INDEX                         { baculaStatsCountersIndex }
          ::= { baculaStatsCountersTable 1 }

          BaculaStatsCountersEntry      ::= SEQUENCE {
            baculaStatsCountersIndex    CounterIndex,

            baculaStatsCounterName      DisplayString
          }

          baculaStatsCountersIndex      OBJECT-TYPE
            SYNTAX                      CounterIndex
            MAX-ACCESS                  not-accessible
            STATUS                      current
            DESCRIPTION                 "Reference Index for each counter name."
            ::= { baculaStatsCountersEntry 1 }

          baculaStatsCounterName        OBJECT-TYPE
            SYNTAX                      DisplayString
            MAX-ACCESS                  read-only
            STATUS                      current
            DESCRIPTION                 "Names of the counter values."
            ::= { baculaStatsCountersEntry 2 }
-- }}}

      -- {{{ .1.3.6.1.4.1.8767.2.3.9  baculaStatsTable
      baculaStatsTable                 OBJECT-TYPE
        SYNTAX                         SEQUENCE OF BaculaStatsEntry
        MAX-ACCESS                     not-accessible
        STATUS                         current
        DESCRIPTION                    "A list of bacula statistic counters"
        ::= { baculaStats 9 }
  
        baculaStatsEntry               OBJECT-TYPE
          SYNTAX                       BaculaStatsEntry
          MAX-ACCESS                   not-accessible
          STATUS                       current
          DESCRIPTION                  "An entry containing bacula statistics"
          INDEX                        { baculaClientsIndex, baculaJobsNameIndex, baculaJobsIDIndex, baculaStatsIndex }
          ::= { baculaStatsTable 1 }
  
          BaculaStatsEntry             ::= SEQUENCE {
            baculaStatsIndex           CounterIndex,

            baculaStatsStart           DisplayString,
            baculaStatsEnd             DisplayString,
            baculaStatsDuration        Integer32,
            baculaStatsFiles           Integer32,
            baculaStatsBytes           Integer32,
            baculaStatsType            DisplayString,
            baculaStatsStatus          BaculaJobStatus,
            baculaStatsLevel           BaculaJobLevel,
            baculaStatsErrors          Integer32,
            baculaStatsMissingFiles    Integer32
          }
  
          baculaStatsIndex             OBJECT-TYPE
            SYNTAX                     CounterIndex
            MAX-ACCESS                 not-accessible
            STATUS                     current
            DESCRIPTION                "Reference Index for each counter."
            ::= { baculaStatsEntry 1 }
  
          baculaStatsStart             OBJECT-TYPE
            SYNTAX                     DisplayString
            MAX-ACCESS                 read-only
            STATUS                     current
            DESCRIPTION                "Date and time of job start."
            ::= { baculaStatsEntry 2 }

          baculaStatsEnd               OBJECT-TYPE
            SYNTAX                     DisplayString
            MAX-ACCESS                 read-only
            STATUS                     current
            DESCRIPTION                "Date and time of job completion."
            ::= { baculaStatsEntry 3 }

          baculaStatsDuration          OBJECT-TYPE
            SYNTAX                     Integer32
            MAX-ACCESS                 read-only
            STATUS                     current
            DESCRIPTION                "Duration of job."
            ::= { baculaStatsEntry 4 }

          baculaStatsFiles             OBJECT-TYPE
            SYNTAX                     Integer32 (1..2147483647)
            MAX-ACCESS                 read-only
            STATUS                     current
            DESCRIPTION                "Files backed up in the job."
            ::= { baculaStatsEntry 5 }

          baculaStatsBytes             OBJECT-TYPE
            SYNTAX                     Integer32
            MAX-ACCESS                 read-only
            STATUS                     current
            DESCRIPTION                "Bytes backed up in the job."
            ::= { baculaStatsEntry 6 }

          baculaStatsType              OBJECT-TYPE
            SYNTAX                     DisplayString
            MAX-ACCESS                 read-only
            STATUS                     current
            DESCRIPTION                "Files backed up in the job."
            ::= { baculaStatsEntry 7 }

          baculaStatsStatus            OBJECT-TYPE
            SYNTAX                     BaculaJobStatus
            MAX-ACCESS                 read-only
            STATUS                     current
            DESCRIPTION                "Files backed up in the job."
            ::= { baculaStatsEntry 8 }

          baculaStatsLevel             OBJECT-TYPE
            SYNTAX                     BaculaJobLevel
            MAX-ACCESS                 read-only
            STATUS                     current
            DESCRIPTION                "Files backed up in the job."
            ::= { baculaStatsEntry 9 }

          baculaStatsErrors            OBJECT-TYPE
            SYNTAX                     Integer32 (1..2147483647)
            MAX-ACCESS                 read-only
            STATUS                     current
            DESCRIPTION                "Files backed up in the job."
            ::= { baculaStatsEntry 10 }

          baculaStatsMissingFiles      OBJECT-TYPE
            SYNTAX                     Integer32 (1..2147483647)
            MAX-ACCESS                 read-only
            STATUS                     current
            DESCRIPTION                "Files backed up in the job."
            ::= { baculaStatsEntry 11 }

-- }}}

      -- {{{ .1.3.6.1.4.1.8767.2.3.10 baculaPoolsTable
      baculaPoolsTable                 OBJECT-TYPE
        SYNTAX                         SEQUENCE OF BaculaPoolsEntry
        MAX-ACCESS                     not-accessible
        STATUS                         current
        DESCRIPTION                    "A list of bacula pool information."
        ::= { baculaStats 10 }
  
        baculaPoolsEntry               OBJECT-TYPE
          SYNTAX                       BaculaPoolsEntry
          MAX-ACCESS                   not-accessible
          STATUS                       current
          DESCRIPTION                  "An entry containing bacula statistics"
          INDEX                        { baculaPoolsIndex }
          ::= { baculaPoolsTable 1 }
  
          BaculaPoolsEntry             ::= SEQUENCE {
            baculaPoolsIndex           CounterIndex,

            baculaPoolsName            DisplayString,
            baculaPoolsNum             Integer32,
            baculaPoolsMax             Integer32,
            baculaPoolsUseOnce         TrueFalse,
            baculaPoolsUseCatalog      TrueFalse,
            baculaPoolsAcceptAnyVolume TrueFalse,
            baculaPoolsRetention       Integer32,
            baculaPoolsDuration        Integer32,
            baculaPoolsMaxJobs         Integer32,
            baculaPoolsMaxFiles        Integer32,
            baculaPoolsMaxBytes        Integer32,
            baculaPoolsAutoPrune       TrueFalse,
            baculaPoolsRecycle         TrueFalse,
            baculaPoolsType            DisplayString,
            baculaPoolsLabelFormat     DisplayString,
            baculaPoolsEnabled         TrueFalse,
            baculaPoolsScratchPoolID   Integer32,
            baculaPoolsRecyclePoolID   Integer32
          }
  
          baculaPoolsIndex             OBJECT-TYPE
            SYNTAX                     CounterIndex
            MAX-ACCESS                 not-accessible
            STATUS                     current
            DESCRIPTION                "Reference Index for each counter."
            ::= { baculaPoolsEntry 1 }
  
          baculaPoolsName              OBJECT-TYPE
            SYNTAX                     DisplayString
            MAX-ACCESS                 read-only
            STATUS                     current
            DESCRIPTION                "Name of Bacula pool."
            ::= { baculaPoolsEntry 2 }

          baculaPoolsNum               OBJECT-TYPE
            SYNTAX                     Integer32
            MAX-ACCESS                 read-only
            STATUS                     current
            DESCRIPTION                "Number of volumes in pool."
            ::= { baculaPoolsEntry 3 }

          baculaPoolsMax               OBJECT-TYPE
            SYNTAX                     Integer32
            MAX-ACCESS                 read-only
            STATUS                     current
            DESCRIPTION                "Maximum number of volumes in pool."
            ::= { baculaPoolsEntry 4 }

          baculaPoolsUseOnce           OBJECT-TYPE
            SYNTAX                     TrueFalse
            MAX-ACCESS                 read-write
            STATUS                     current
            DESCRIPTION                "Use pool only once."
            ::= { baculaPoolsEntry 5 }

          baculaPoolsUseCatalog        OBJECT-TYPE
            SYNTAX                     TrueFalse
            MAX-ACCESS                 read-write
            STATUS                     current
            DESCRIPTION                "Use catalog."
            ::= { baculaPoolsEntry 6 }

          baculaPoolsAcceptAnyVolume   OBJECT-TYPE
            SYNTAX                     TrueFalse
            MAX-ACCESS                 read-write
            STATUS                     current
            DESCRIPTION                "Accept any volume into pool."
            ::= { baculaPoolsEntry 7 }

          baculaPoolsRetention         OBJECT-TYPE
            SYNTAX                     Integer32
            MAX-ACCESS                 read-write
            STATUS                     current
            DESCRIPTION                "Pool retention period (sec)."
            ::= { baculaPoolsEntry 8 }

          baculaPoolsDuration          OBJECT-TYPE
            SYNTAX                     Integer32
            MAX-ACCESS                 read-write
            STATUS                     current
            DESCRIPTION                "Pool duration period (sec)."
            ::= { baculaPoolsEntry 9 }

          baculaPoolsMaxJobs           OBJECT-TYPE
            SYNTAX                     Integer32 (0..10)
            MAX-ACCESS                 read-write
            STATUS                     current
            DESCRIPTION                "Maximum jobs that can use pool."
            ::= { baculaPoolsEntry 10 }

          baculaPoolsMaxFiles          OBJECT-TYPE
            SYNTAX                     Integer32 (0..10)
            MAX-ACCESS                 read-write
            STATUS                     current
            DESCRIPTION                "Maximum files in pool."
            ::= { baculaPoolsEntry 11 }

          baculaPoolsMaxBytes          OBJECT-TYPE
            SYNTAX                     Integer32
            MAX-ACCESS                 read-write
            STATUS                     current
            DESCRIPTION                "Maximum bytes in pool."
            ::= { baculaPoolsEntry 12 }

          baculaPoolsAutoPrune         OBJECT-TYPE
            SYNTAX                     TrueFalse
            MAX-ACCESS                 read-write
            STATUS                     current
            DESCRIPTION                "Auto prune volumes in pool."
            ::= { baculaPoolsEntry 13 }

          baculaPoolsRecycle           OBJECT-TYPE
            SYNTAX                     TrueFalse
            MAX-ACCESS                 read-write
            STATUS                     current
            DESCRIPTION                "Recycle volumes in pool."
            ::= { baculaPoolsEntry 14 }

          baculaPoolsType              OBJECT-TYPE
            SYNTAX                     DisplayString
            MAX-ACCESS                 read-write
            STATUS                     current
            DESCRIPTION                "Type of pool."
            ::= { baculaPoolsEntry 15 }

          baculaPoolsLabelFormat       OBJECT-TYPE
            SYNTAX                     DisplayString
            MAX-ACCESS                 read-write
            STATUS                     current
            DESCRIPTION                "Pool label format."
            ::= { baculaPoolsEntry 16 }

          baculaPoolsEnabled           OBJECT-TYPE
            SYNTAX                     TrueFalse
            MAX-ACCESS                 read-write
            STATUS                     current
            DESCRIPTION                "Enable pool."
            ::= { baculaPoolsEntry 17 }

          baculaPoolsScratchPoolID     OBJECT-TYPE
            SYNTAX                     Integer32
            MAX-ACCESS                 read-only
            STATUS                     current
            DESCRIPTION                "Scratch pool ID."
            ::= { baculaPoolsEntry 18 }

          baculaPoolsRecyclePoolID     OBJECT-TYPE
            SYNTAX                     Integer32
            MAX-ACCESS                 read-only
            STATUS                     current
            DESCRIPTION                "Recycle pool ID."
            ::= { baculaPoolsEntry 19 }
-- }}}

      -- {{{ .1.3.6.1.4.1.8767.2.3.11 baculaMediaTable
      baculaMediaTable                 OBJECT-TYPE
        SYNTAX                         SEQUENCE OF BaculaMediaEntry
        MAX-ACCESS                     not-accessible
        STATUS                         current
        DESCRIPTION                    "A list of bacula media information."
        ::= { baculaStats 11 }
  
        baculaMediaEntry               OBJECT-TYPE
          SYNTAX                       BaculaMediaEntry
          MAX-ACCESS                   not-accessible
          STATUS                       current
          DESCRIPTION                  "An entry containing bacula statistics"
          INDEX                        { baculaMediaIndex }
          ::= { baculaMediaTable 1 }
  
          BaculaMediaEntry             ::= SEQUENCE {
            baculaMediaIndex           CounterIndex,

            baculaMediaName            DisplayString,
            baculaMediaSlot            Integer32,
            baculaMediaPool            Integer32,
            baculaMediaType            DisplayString,
            baculaMediaWrittenFirst    DisplayString,
            baculaMediaWrittenLast     DisplayString,
            baculaMediaLabelDate       DisplayString,
            baculaMediaJobs            Integer32,
            baculaMediaFiles           Integer32,
            baculaMediaBlocks          Integer32,
            baculaMediaMounts          Integer32,
            baculaMediaBytes           Integer32,
            baculaMediaErrors          Integer32,
            baculaMediaWrites          Integer32,
            baculaMediaCapacity        Integer32,
            baculaMediaStatus          BaculaVolumeStatus,
            baculaMediaRecycle         TrueFalse,
            baculaMediaRetention       Integer32,
            baculaMediaDuration        Integer32,
            baculaMediaMaxJobs         Integer32,
            baculaMediaMaxFiles        Integer32,
            baculaMediaMaxBytes        Integer32,
            baculaMediaInChanger       TrueFalse,
            baculaMediaMediaAddressing TrueFalse,
            baculaMediaReadTime        Integer32,
            baculaMediaWriteTime       Integer32,
            baculaMediaEndFile         Integer32,
            baculaMediaEndBlock        Integer32
          }
  
          baculaMediaIndex             OBJECT-TYPE
            SYNTAX                     CounterIndex
            MAX-ACCESS                 not-accessible
            STATUS                     current
            DESCRIPTION                "Reference Index for each counter."
            ::= { baculaMediaEntry 1 }
  
          baculaMediaName              OBJECT-TYPE
            SYNTAX                     DisplayString
            MAX-ACCESS                 read-only
            STATUS                     current
            DESCRIPTION                "Name of Bacula pool."
            ::= { baculaMediaEntry 2 }

          baculaMediaSlot              OBJECT-TYPE
            SYNTAX                     Integer32
            MAX-ACCESS                 read-only
            STATUS                     current
            DESCRIPTION                "."
            ::= { baculaMediaEntry 3 }

          baculaMediaPool              OBJECT-TYPE
            SYNTAX                     Integer32
            MAX-ACCESS                 read-only
            STATUS                     current
            DESCRIPTION                "."
            ::= { baculaMediaEntry 4 }

          baculaMediaType              OBJECT-TYPE
            SYNTAX                     DisplayString
            MAX-ACCESS                 read-only
            STATUS                     current
            DESCRIPTION                "."
            ::= { baculaMediaEntry 5 }

          baculaMediaWrittenFirst      OBJECT-TYPE
            SYNTAX                     DisplayString
            MAX-ACCESS                 read-only
            STATUS                     current
            DESCRIPTION                "."
            ::= { baculaMediaEntry 6 }

          baculaMediaWrittenLast       OBJECT-TYPE
            SYNTAX                     DisplayString
            MAX-ACCESS                 read-only
            STATUS                     current
            DESCRIPTION                "."
            ::= { baculaMediaEntry 7 }

          baculaMediaLabelDate         OBJECT-TYPE
            SYNTAX                     DisplayString
            MAX-ACCESS                 read-only
            STATUS                     current
            DESCRIPTION                "."
            ::= { baculaMediaEntry 8 }

          baculaMediaJobs              OBJECT-TYPE
            SYNTAX                     Integer32
            MAX-ACCESS                 read-only
            STATUS                     current
            DESCRIPTION                "."
            ::= { baculaMediaEntry 9 }

          baculaMediaFiles             OBJECT-TYPE
            SYNTAX                     Integer32
            MAX-ACCESS                 read-only
            STATUS                     current
            DESCRIPTION                "."
            ::= { baculaMediaEntry 10 }

          baculaMediaBlocks            OBJECT-TYPE
            SYNTAX                     Integer32
            MAX-ACCESS                 read-only
            STATUS                     current
            DESCRIPTION                "."
            ::= { baculaMediaEntry 11 }

          baculaMediaMounts            OBJECT-TYPE
            SYNTAX                     Integer32
            MAX-ACCESS                 read-only
            STATUS                     current
            DESCRIPTION                "."
            ::= { baculaMediaEntry 12 }

          baculaMediaBytes             OBJECT-TYPE
            SYNTAX                     Integer32
            MAX-ACCESS                 read-only
            STATUS                     current
            DESCRIPTION                "."
            ::= { baculaMediaEntry 13 }

          baculaMediaErrors             OBJECT-TYPE
            SYNTAX                     Integer32
            MAX-ACCESS                 read-only
            STATUS                     current
            DESCRIPTION                "."
            ::= { baculaMediaEntry 14 }

          baculaMediaWrites            OBJECT-TYPE
            SYNTAX                     Integer32
            MAX-ACCESS                 read-only
            STATUS                     current
            DESCRIPTION                "."
            ::= { baculaMediaEntry 15 }

          baculaMediaCapacity          OBJECT-TYPE
            SYNTAX                     Integer32
            MAX-ACCESS                 read-only
            STATUS                     current
            DESCRIPTION                "."
            ::= { baculaMediaEntry 16 }

          baculaMediaStatus            OBJECT-TYPE
            SYNTAX                     BaculaVolumeStatus
            MAX-ACCESS                 read-only
            STATUS                     current
            DESCRIPTION                "."
            ::= { baculaMediaEntry 17 }

          baculaMediaRecycle           OBJECT-TYPE
            SYNTAX                     TrueFalse
            MAX-ACCESS                 read-only
            STATUS                     current
            DESCRIPTION                "."
            ::= { baculaMediaEntry 18 }

          baculaMediaRetention         OBJECT-TYPE
            SYNTAX                     Integer32
            MAX-ACCESS                 read-only
            STATUS                     current
            DESCRIPTION                "."
            ::= { baculaMediaEntry 19 }

          baculaMediaDuration          OBJECT-TYPE
            SYNTAX                     Integer32
            MAX-ACCESS                 read-only
            STATUS                     current
            DESCRIPTION                "."
            ::= { baculaMediaEntry 20 }

          baculaMediaMaxJobs           OBJECT-TYPE
            SYNTAX                     Integer32
            MAX-ACCESS                 read-only
            STATUS                     current
            DESCRIPTION                "."
            ::= { baculaMediaEntry 21 }

          baculaMediaMaxFiles          OBJECT-TYPE
            SYNTAX                     Integer32
            MAX-ACCESS                 read-only
            STATUS                     current
            DESCRIPTION                "."
            ::= { baculaMediaEntry 22 }

          baculaMediaMaxBytes          OBJECT-TYPE
            SYNTAX                     Integer32
            MAX-ACCESS                 read-only
            STATUS                     current
            DESCRIPTION                "."
            ::= { baculaMediaEntry 23 }

          baculaMediaInChanger         OBJECT-TYPE
            SYNTAX                     TrueFalse
            MAX-ACCESS                 read-only
            STATUS                     current
            DESCRIPTION                "."
            ::= { baculaMediaEntry 24 }

          baculaMediaMediaAddressing   OBJECT-TYPE
            SYNTAX                     TrueFalse
            MAX-ACCESS                 read-only
            STATUS                     current
            DESCRIPTION                "."
            ::= { baculaMediaEntry 25 }

          baculaMediaReadTime          OBJECT-TYPE
            SYNTAX                     Integer32
            MAX-ACCESS                 read-only
            STATUS                     current
            DESCRIPTION                "."
            ::= { baculaMediaEntry 26 }

          baculaMediaWriteTime         OBJECT-TYPE
            SYNTAX                     Integer32
            MAX-ACCESS                 read-only
            STATUS                     current
            DESCRIPTION                "."
            ::= { baculaMediaEntry 27 }

          baculaMediaEndFile           OBJECT-TYPE
            SYNTAX                     Integer32
            MAX-ACCESS                 read-only
            STATUS                     current
            DESCRIPTION                "."
            ::= { baculaMediaEntry 28 }

          baculaMediaEndBlock          OBJECT-TYPE
            SYNTAX                     Integer32
            MAX-ACCESS                 read-only
            STATUS                     current
            DESCRIPTION                "."
            ::= { baculaMediaEntry 29 }
-- }}}
-- }}}

    -- {{{ .1.3.6.1.4.1.8767.2.4 systemStats
    systemStats                        OBJECT IDENTIFIER ::= { snmp 4 }
      -- {{{ .1.3.6.1.4.1.8767.2.4.1    systemUptime
      systemUptime                     OBJECT-TYPE
        SYNTAX                         Integer32
        MAX-ACCESS                     read-only
        STATUS                         current
        DESCRIPTION                    "System uptime (in seconds)."
        ::= { systemStats 1 }
-- }}}


      -- {{{ .1.3.6.1.4.1.8767.2.4.2    systemMemoryTotal
      systemMemoryTotal            OBJECT-TYPE
        SYNTAX                     Integer32
        MAX-ACCESS                 read-only
        STATUS                     current
        DESCRIPTION                "Total physical memory in the system."
        ::= { systemStats 2 }
-- }}}

      -- {{{ .1.3.6.1.4.1.8767.2.4.3    systemMemoryUsed
      systemMemoryUsed             OBJECT-TYPE
        SYNTAX                     Integer32
        MAX-ACCESS                 read-only
        STATUS                     current
        DESCRIPTION                "Physical memory in use by the system."
        ::= { systemStats 3 }
-- }}}

      -- {{{ .1.3.6.1.4.1.8767.2.4.4    systemMemoryFree
      systemMemoryFree             OBJECT-TYPE
        SYNTAX                     Integer32
        MAX-ACCESS                 read-only
        STATUS                     current
        DESCRIPTION                "Physical memory free the system."
        ::= { systemStats 4 }
-- }}}

      -- {{{ .1.3.6.1.4.1.8767.2.4.5    systemMemoryBuffered
      systemMemoryBuffered         OBJECT-TYPE
        SYNTAX                     Integer32
        MAX-ACCESS                 read-only
        STATUS                     current
        DESCRIPTION                "Memory buffered in the system."
        ::= { systemStats 5 }
-- }}}

      -- {{{ .1.3.6.1.4.1.8767.2.4.6    systemMemoryCached
      systemMemoryCached           OBJECT-TYPE
        SYNTAX                     Integer32
        MAX-ACCESS                 read-only
        STATUS                     current
        DESCRIPTION                "Memory cached in the system."
        ::= { systemStats 6 }
-- }}}

      -- {{{ .1.3.6.1.4.1.8767.2.4.7    systemMemorySwapTotal
      systemMemorySwapTotal        OBJECT-TYPE
        SYNTAX                     Integer32
        MAX-ACCESS                 read-only
        STATUS                     current
        DESCRIPTION                "Total amount of swap space in the system."
        ::= { systemStats 7 }
-- }}}

      -- {{{ .1.3.6.1.4.1.8767.2.4.8    systemMemorySwapUsed
      systemMemorySwapUsed         OBJECT-TYPE
        SYNTAX                     Integer32
        MAX-ACCESS                 read-only
        STATUS                     current
        DESCRIPTION                "Swap memory in use by the system."
        ::= { systemStats 8 }
-- }}}

      -- {{{ .1.3.6.1.4.1.8767.2.4.9    systemMemorySwapFree
      systemMemorySwapFree         OBJECT-TYPE
        SYNTAX                     Integer32
        MAX-ACCESS                 read-only
        STATUS                     current
        DESCRIPTION                "Swap memory free in the system."
        ::= { systemStats 9 }
-- }}}


      -- {{{ .1.3.6.1.4.1.8767.2.4.10   systemCPUTasksTotal
      systemCPUTasksTotal          OBJECT-TYPE
        SYNTAX                     Integer32
        MAX-ACCESS                 read-only
        STATUS                     current
        DESCRIPTION                "."
        ::= { systemStats 10 }
-- }}}

      -- {{{ .1.3.6.1.4.1.8767.2.4.11   systemCPUTasksRunning
      systemCPUTasksRunning        OBJECT-TYPE
        SYNTAX                     Integer32
        MAX-ACCESS                 read-only
        STATUS                     current
        DESCRIPTION                "."
        ::= { systemStats 11 }
-- }}}

      -- {{{ .1.3.6.1.4.1.8767.2.4.12   systemCPUTasksSleeping
      systemCPUTasksSleeping       OBJECT-TYPE
        SYNTAX                     Integer32
        MAX-ACCESS                 read-only
        STATUS                     current
        DESCRIPTION                "."
        ::= { systemStats 12 }
-- }}}

      -- {{{ .1.3.6.1.4.1.8767.2.4.13   systemCPUTasksStopped
      systemCPUTasksStopped        OBJECT-TYPE
        SYNTAX                     Integer32
        MAX-ACCESS                 read-only
        STATUS                     current
        DESCRIPTION                "."
        ::= { systemStats 13 }
-- }}}

      -- {{{ .1.3.6.1.4.1.8767.2.4.14   systemCPUTasksZombies
      systemCPUTasksZombies        OBJECT-TYPE
        SYNTAX                     Integer32
        MAX-ACCESS                 read-only
        STATUS                     current
        DESCRIPTION                "."
        ::= { systemStats 14 }
-- }}}

      -- {{{ .1.3.6.1.4.1.8767.2.4.15   systemCPUUsageUser
      systemCPUUsageUser           OBJECT-TYPE
        SYNTAX                     Integer32
        MAX-ACCESS                 read-only
        STATUS                     current
        DESCRIPTION                "."
        ::= { systemStats 15 }
-- }}}

      -- {{{ .1.3.6.1.4.1.8767.2.4.16   systemCPUUsageSystem
      systemCPUUsageSystem         OBJECT-TYPE
        SYNTAX                     Integer32
        MAX-ACCESS                 read-only
        STATUS                     current
        DESCRIPTION                "."
        ::= { systemStats 16 }
-- }}}

      -- {{{ .1.3.6.1.4.1.8767.2.4.17   systemCPUUsageNice
      systemCPUUsageNice           OBJECT-TYPE
        SYNTAX                     Integer32
        MAX-ACCESS                 read-only
        STATUS                     current
        DESCRIPTION                "."
        ::= { systemStats 17 }
-- }}}

      -- {{{ .1.3.6.1.4.1.8767.2.4.18   systemCPUUsageIdle
      systemCPUUsageIdle           OBJECT-TYPE
        SYNTAX                     Integer32
        MAX-ACCESS                 read-only
        STATUS                     current
        DESCRIPTION                "."
        ::= { systemStats 18 }
-- }}}

      -- {{{ .1.3.6.1.4.1.8767.2.4.19   systemCPUUsageIOWait
      systemCPUUsageIOWait         OBJECT-TYPE
        SYNTAX                     Integer32
        MAX-ACCESS                 read-only
        STATUS                     current
        DESCRIPTION                "."
        ::= { systemStats 19 }
-- }}}


      -- {{{ .1.3.6.1.4.1.8767.2.4.20   systemLoadLastOne
      systemLoadLastOne            OBJECT-TYPE
        SYNTAX                     Integer32
        MAX-ACCESS                 read-only
        STATUS                     current
        DESCRIPTION                "."
        ::= { systemStats 20 }
-- }}}

      -- {{{ .1.3.6.1.4.1.8767.2.4.21   systemLoadLastFive
      systemLoadLastFive           OBJECT-TYPE
        SYNTAX                     Integer32
        MAX-ACCESS                 read-only
        STATUS                     current
        DESCRIPTION                "."
        ::= { systemStats 21 }
-- }}}

      -- {{{ .1.3.6.1.4.1.8767.2.4.22   systemLoadLastFifteen
      systemLoadLastFifteen        OBJECT-TYPE
        SYNTAX                     Integer32
        MAX-ACCESS                 read-only
        STATUS                     current
        DESCRIPTION                "."
        ::= { systemStats 22 }
-- }}}
-- }}}

    -- {{{ .1.3.6.1.4.1.8767.2.5 packageStats
    packageStats                       OBJECT IDENTIFIER ::= { snmp 5 }
      -- {{{ .1.3.6.1.4.1.8767.2.5.1 packageStatsTable
      packageStatsTable                    OBJECT-TYPE
        SYNTAX                             SEQUENCE OF PackageStatsEntry
        MAX-ACCESS                         not-accessible
        STATUS                             current
        DESCRIPTION                        "A list of package statistic information."
        ::= { packageStats 1 }

        packageStatsEntry                  OBJECT-TYPE
          SYNTAX                           PackageStatsEntry
          MAX-ACCESS                       not-accessible
          STATUS                           current
          DESCRIPTION                      "Package statistics table"
          INDEX                            { packageIndexStats }
          ::= { packageStatsTable 1 }

          PackageStatsEntry                ::= SEQUENCE {
            packageIndexStats              CounterIndex,

            packageName                    DisplayString,
            packageVersion                 DisplayString,
            packageDesc                    DisplayString,
            packageStatus                  DisplayString
          }

          packageIndexStats                OBJECT-TYPE
            SYNTAX                         CounterIndex
            MAX-ACCESS                     not-accessible
            STATUS                         current
            DESCRIPTION                    "Reference Index for each counter."
            ::= { packageStatsEntry 1 }

          packageName                      OBJECT-TYPE
            SYNTAX                         DisplayString
            MAX-ACCESS                     read-only
            STATUS                         current
            DESCRIPTION                    "Name of package"
            ::= { packageStatsEntry 2 }

          packageVersion                   OBJECT-TYPE
            SYNTAX                         DisplayString
            MAX-ACCESS                     read-only
            STATUS                         current
            DESCRIPTION                    "xx"
            ::= { packageStatsEntry 3 }

          packageDesc                      OBJECT-TYPE
            SYNTAX                         DisplayString
            MAX-ACCESS                     read-only
            STATUS                         current
            DESCRIPTION                    "xx"
            ::= { packageStatsEntry 4 }

          packageStatus                    OBJECT-TYPE
            SYNTAX                         DisplayString
            MAX-ACCESS                     read-only
            STATUS                         current
            DESCRIPTION                    "xx"
            ::= { packageStatsEntry 5 }
-- }}}

      -- {{{ .1.3.6.1.4.1.8767.2.5.2 packageInfoTable
      packageInfoTable                     OBJECT-TYPE
        SYNTAX                             SEQUENCE OF PackageInfoEntry
        MAX-ACCESS                         not-accessible
        STATUS                             current
        DESCRIPTION                        "Package statistics table"
        ::= { packageStats 2 }

        packageInfoEntry                   OBJECT-TYPE
          SYNTAX                           PackageInfoEntry
          MAX-ACCESS                       not-accessible
          STATUS                           current
          DESCRIPTION                      "Package statistics table"
          INDEX                            { packageIndexInfo }
          ::= { packageInfoTable 1 }

          PackageInfoEntry                ::= SEQUENCE {
            packageIndexInfo              CounterIndex,

            packagePriority               DisplayString,
            packageSection                DisplayString,
            packageMaintainer             DisplayString,
            packageSource                 DisplayString,
            packageDepends                DisplayString,
            packageRecommends             DisplayString,
            packageSuggests               DisplayString,
            packageSize                   DisplayString,
            packageMD5Sum                 DisplayString
          }

          packageIndexInfo                 OBJECT-TYPE
            SYNTAX                         CounterIndex
            MAX-ACCESS                     not-accessible
            STATUS                         current
            DESCRIPTION                    "Reference Index for each counter."
            ::= { packageInfoEntry  1 }

          packagePriority                  OBJECT-TYPE
            SYNTAX                         DisplayString
            MAX-ACCESS                     read-only
            STATUS                         current
            DESCRIPTION                    "xx"
            ::= { packageInfoEntry  2 }

          packageSection                   OBJECT-TYPE
            SYNTAX                         DisplayString
            MAX-ACCESS                     read-only
            STATUS                         current
            DESCRIPTION                    "xx"
            ::= { packageInfoEntry  3 }

          packageMaintainer                OBJECT-TYPE
            SYNTAX                         DisplayString
            MAX-ACCESS                     read-only
            STATUS                         current
            DESCRIPTION                    "xx"
            ::= { packageInfoEntry  4 }

          packageSource                    OBJECT-TYPE
            SYNTAX                         DisplayString
            MAX-ACCESS                     read-only
            STATUS                         current
            DESCRIPTION                    "xx"
            ::= { packageInfoEntry  5 }

          packageDepends                   OBJECT-TYPE
            SYNTAX                         DisplayString
            MAX-ACCESS                     read-only
            STATUS                         current
            DESCRIPTION                    "xx"
            ::= { packageInfoEntry  6 }

          packageRecommends                OBJECT-TYPE
            SYNTAX                         DisplayString
            MAX-ACCESS                     read-only
            STATUS                         current
            DESCRIPTION                    "xx"
            ::= { packageInfoEntry  7 }

          packageSuggests                  OBJECT-TYPE
            SYNTAX                         DisplayString
            MAX-ACCESS                     read-only
            STATUS                         current
            DESCRIPTION                    "xx"
            ::= { packageInfoEntry  8 }

          packageSize                      OBJECT-TYPE
            SYNTAX                         DisplayString
            MAX-ACCESS                     read-only
            STATUS                         current
            DESCRIPTION                    "xx"
            ::= { packageInfoEntry  9 }

          packageMD5Sum                    OBJECT-TYPE
            SYNTAX                         DisplayString
            MAX-ACCESS                     read-only
            STATUS                         current
            DESCRIPTION                    "xx"
            ::= { packageInfoEntry 10 }
-- }}}
-- }}}

    -- {{{ .1.3.6.1.4.1.8767.2.6 zfsStats
    zfsStats                           OBJECT IDENTIFIER ::= { snmp 6 }
      -- {{{ .1.3.6.1.4.1.8767.2.6.[1-4] zfsTotal{Pools,Datasets,Volumes,Snapshots}
      zfsTotalPools                    OBJECT-TYPE
        SYNTAX                         Integer32
        MAX-ACCESS                     read-only
        STATUS                         current
        DESCRIPTION                    "Total number of ZFS Pools."
        ::= { zfsStats 1 }

      zfsTotalDatasets                 OBJECT-TYPE
        SYNTAX                         Integer32
        MAX-ACCESS                     read-only
        STATUS                         current
        DESCRIPTION                    "Total number of ZFS Filesystems."
        ::= { zfsStats 2 }

      zfsTotalVolumes                  OBJECT-TYPE
        SYNTAX                         Integer32
        MAX-ACCESS                     read-only
        STATUS                         current
        DESCRIPTION                    "Total number of ZFS Volumes."
        ::= { zfsStats 3 }

      zfsTotalSnapshots                OBJECT-TYPE
        SYNTAX                         Integer32
        MAX-ACCESS                     read-only
        STATUS                         current
        DESCRIPTION                    "Total number of ZFS Snapshots."
        ::= { zfsStats 4 }
-- }}}

      -- {{{ .1.3.6.1.4.1.8767.2.6.5 zfsPoolStatusTable
      zfsPoolStatusTable               OBJECT-TYPE
        SYNTAX                         SEQUENCE OF ZFSPoolStatusEntry
        MAX-ACCESS                     not-accessible
        STATUS                         current
        DESCRIPTION                    "A list of ZFS pool status information."
        ::= { zfsStats 5 }

        zfsPoolStatusEntry             OBJECT-TYPE
          SYNTAX                       ZFSPoolStatusEntry
          MAX-ACCESS                   not-accessible
          STATUS                       current
          DESCRIPTION                  "An entry containing ZFS pool status values."
          INDEX                        { zfsPoolStatusIndex }
          ::= { zfsPoolStatusTable 1 }

          ZFSPoolStatusEntry           ::= SEQUENCE {
            zfsPoolStatusIndex         CounterIndex,

            zfsPoolName                DisplayString,
            zfsPoolGUID                DisplayString,
            zfsPoolSize                Integer64,
            zfsPoolAlloc               Integer64,
            zfsPoolFree                Integer64,
            zfsPoolCap                 Integer32,
            zfsPoolDedup               DisplayString,
            zfsPoolHealth              ZFSPoolStatusValue,
            zfsPoolAltRoot             DisplayString,
            zfsPoolUsedBySnaps         Integer32,
            zfsPoolUsed                Integer32
          }

          zfsPoolStatusIndex           OBJECT-TYPE
            SYNTAX                     CounterIndex
            MAX-ACCESS                 not-accessible
            STATUS                     current
            DESCRIPTION                "Reference Index for each counter."
            ::= { zfsPoolStatusEntry 1 }

          zfsPoolName                  OBJECT-TYPE
            SYNTAX                     DisplayString
            MAX-ACCESS                 read-only
            STATUS                     current
            DESCRIPTION                "Name of ZFS pool."
            ::= { zfsPoolStatusEntry 2 }

          zfsPoolGUID                  OBJECT-TYPE
            SYNTAX                     DisplayString
            MAX-ACCESS                 read-only
            STATUS                     current
            DESCRIPTION                "GUID of ZFS pool."
            ::= { zfsPoolStatusEntry 3 }

          zfsPoolSize                  OBJECT-TYPE
            SYNTAX                     Integer64
            MAX-ACCESS                 read-only
            STATUS                     current
            DESCRIPTION                "."
            ::= { zfsPoolStatusEntry 4 }

          zfsPoolAlloc                 OBJECT-TYPE
            SYNTAX                     Integer64
            MAX-ACCESS                 read-only
            STATUS                     current
            DESCRIPTION                "."
            ::= { zfsPoolStatusEntry 5 }

          zfsPoolFree                  OBJECT-TYPE
            SYNTAX                     Integer64
            MAX-ACCESS                 read-only
            STATUS                     current
            DESCRIPTION                "."
            ::= { zfsPoolStatusEntry 6 }

          zfsPoolCap                   OBJECT-TYPE
            SYNTAX                     Integer32
            MAX-ACCESS                 read-only
            STATUS                     current
            DESCRIPTION                "."
            ::= { zfsPoolStatusEntry 7 }

          zfsPoolDedup                 OBJECT-TYPE
            SYNTAX                     DisplayString
            MAX-ACCESS                 read-only
            STATUS                     current
            DESCRIPTION                "."
            ::= { zfsPoolStatusEntry 8 }

          zfsPoolHealth                OBJECT-TYPE
            SYNTAX                     ZFSPoolStatusValue
            MAX-ACCESS                 read-only
            STATUS                     current
            DESCRIPTION                "."
            ::= { zfsPoolStatusEntry 9 }

          zfsPoolAltRoot               OBJECT-TYPE
            SYNTAX                     DisplayString
            MAX-ACCESS                 read-only
            STATUS                     current
            DESCRIPTION                "."
            ::= { zfsPoolStatusEntry 10 }

          zfsPoolUsedBySnaps           OBJECT-TYPE
            SYNTAX                     Integer32
            MAX-ACCESS                 read-only
            STATUS                     current
            DESCRIPTION                "."
            ::= { zfsPoolStatusEntry 11 }

          zfsPoolUsed                  OBJECT-TYPE
            SYNTAX                     Integer32
            MAX-ACCESS                 read-only
            STATUS                     current
            DESCRIPTION                "."
            ::= { zfsPoolStatusEntry 12 }
-- }}}

      -- {{{ .1.3.6.1.4.1.8767.2.6.6 zfsARCUsageTable
      zfsARCUsageTable                 OBJECT-TYPE
        SYNTAX                         SEQUENCE OF ZFSARCUsageEntry
        MAX-ACCESS                     not-accessible
        STATUS                         current
        DESCRIPTION                    "A list of ZFS ARC status information."
        ::= { zfsStats 6 }

        zfsARCUsageEntry               OBJECT-TYPE
          SYNTAX                       ZFSARCUsageEntry
          MAX-ACCESS                   not-accessible
          STATUS                       current
          DESCRIPTION                  "An entry containing ZFS ARC status values."
          INDEX                        { zfsARCUsageIndex }
          ::= { zfsARCUsageTable 1 }

          ZFSARCUsageEntry             ::= SEQUENCE {
            zfsARCUsageIndex           CounterIndex,

            zfsARCMetaMax              Counter32,
            zfsARCMetaUsed             Counter32,
            zfsARCMetaLimit            Counter32,
            zfsARCCMax                 Counter32,
            zfsARCSize                 Counter32
          }

          zfsARCUsageIndex             OBJECT-TYPE
            SYNTAX                     CounterIndex
            MAX-ACCESS                 not-accessible
            STATUS                     current
            DESCRIPTION                "Reference Index for each counter."
            ::= { zfsARCUsageEntry 1 }

          zfsARCMetaMax                OBJECT-TYPE
            SYNTAX                     Counter32
            MAX-ACCESS                 read-only
            STATUS                     current
            DESCRIPTION                "."
            ::= { zfsARCUsageEntry 2 }

          zfsARCMetaUsed               OBJECT-TYPE
            SYNTAX                     Counter32
            MAX-ACCESS                 read-only
            STATUS                     current
            DESCRIPTION                "."
            ::= { zfsARCUsageEntry 3 }

          zfsARCMetaLimit              OBJECT-TYPE
            SYNTAX                     Counter32
            MAX-ACCESS                 read-only
            STATUS                     current
            DESCRIPTION                "."
            ::= { zfsARCUsageEntry 4 }

          zfsARCCMax                   OBJECT-TYPE
            SYNTAX                     Counter32
            MAX-ACCESS                 read-only
            STATUS                     current
            DESCRIPTION                "."
            ::= { zfsARCUsageEntry 5 }

          zfsARCSize                   OBJECT-TYPE
            SYNTAX                     Counter32
            MAX-ACCESS                 read-only
            STATUS                     current
            DESCRIPTION                "."
            ::= { zfsARCUsageEntry 6 }
-- }}}

      -- {{{ .1.3.6.1.4.1.8767.2.6.7 zfsARCStatsTable
      zfsARCStatsTable                 OBJECT-TYPE
        SYNTAX                         SEQUENCE OF ZFSARCStatsEntry
        MAX-ACCESS                     not-accessible
        STATUS                         current
        DESCRIPTION                    "A list of ZFS ARC status information."
        ::= { zfsStats 7 }

        zfsARCStatsEntry               OBJECT-TYPE
          SYNTAX                       ZFSARCStatsEntry
          MAX-ACCESS                   not-accessible
          STATUS                       current
          DESCRIPTION                  "An entry containing ZFS ARC status values."
          INDEX                        { zfsARCStatsIndex }
          ::= { zfsARCStatsTable 1 }

          ZFSARCStatsEntry             ::= SEQUENCE {
            zfsARCStatsIndex           CounterIndex,

            zfsARCHits                 Counter32,
            zfsARCMisses               Counter32,
            zfsARCDemandDataHits       Counter32,
            zfsARCDemandDataMisses     Counter32,
            zfsARCDemandMetaHits       Counter32,
            zfsARCDemandMetaMisses     Counter32,
            zfsARCPrefetchDataHits     Counter32,
            zfsARCPrefetchDataMisses   Counter32,
            zfsARCPrefetchMetaHits     Counter32,
            zfsARCPrefetchMetaMisses   Counter32,
            zfsARCL2Size               Counter32,
            zfsARCL2ASize              Counter32,
            zfsARCL2Hits               Counter32,
            zfsARCL2Misses             Counter32
          }

          zfsARCStatsIndex             OBJECT-TYPE
            SYNTAX                     CounterIndex
            MAX-ACCESS                 not-accessible
            STATUS                     current
            DESCRIPTION                "Reference Index for each counter."
            ::= { zfsARCStatsEntry 1 }

          zfsARCHits                   OBJECT-TYPE
            SYNTAX                     Counter32
            MAX-ACCESS                 read-only
            STATUS                     current
            DESCRIPTION                "."
            ::= { zfsARCStatsEntry 2 }

          zfsARCMisses                 OBJECT-TYPE
            SYNTAX                     Counter32
            MAX-ACCESS                 read-only
            STATUS                     current
            DESCRIPTION                "."
            ::= { zfsARCStatsEntry 3 }

          zfsARCDemandDataHits         OBJECT-TYPE
            SYNTAX                     Counter32
            MAX-ACCESS                 read-only
            STATUS                     current
            DESCRIPTION                "."
            ::= { zfsARCStatsEntry 4 }

          zfsARCDemandDataMisses       OBJECT-TYPE
            SYNTAX                     Counter32
            MAX-ACCESS                 read-only
            STATUS                     current
            DESCRIPTION                "."
            ::= { zfsARCStatsEntry 5 }

          zfsARCDemandMetaHits         OBJECT-TYPE
            SYNTAX                     Counter32
            MAX-ACCESS                 read-only
            STATUS                     current
            DESCRIPTION                "."
            ::= { zfsARCStatsEntry 6 }

          zfsARCDemandMetaMisses       OBJECT-TYPE
            SYNTAX                     Counter32
            MAX-ACCESS                 read-only
            STATUS                     current
            DESCRIPTION                "."
            ::= { zfsARCStatsEntry 7 }

          zfsARCPrefetchDataHits       OBJECT-TYPE
            SYNTAX                     Counter32
            MAX-ACCESS                 read-only
            STATUS                     current
            DESCRIPTION                "."
            ::= { zfsARCStatsEntry 8 }

          zfsARCPrefetchDataMisses     OBJECT-TYPE
            SYNTAX                     Counter32
            MAX-ACCESS                 read-only
            STATUS                     current
            DESCRIPTION                "."
            ::= { zfsARCStatsEntry 9 }

          zfsARCPrefetchMetaHits       OBJECT-TYPE
            SYNTAX                     Counter32
            MAX-ACCESS                 read-only
            STATUS                     current
            DESCRIPTION                "."
            ::= { zfsARCStatsEntry 10 }

          zfsARCPrefetchMetaMisses     OBJECT-TYPE
            SYNTAX                     Counter32
            MAX-ACCESS                 read-only
            STATUS                     current
            DESCRIPTION                "."
            ::= { zfsARCStatsEntry 11 }

          zfsARCL2Size                 OBJECT-TYPE
            SYNTAX                     Counter32
            MAX-ACCESS                 read-only
            STATUS                     current
            DESCRIPTION                "."
            ::= { zfsARCStatsEntry 12 }

          zfsARCL2ASize                OBJECT-TYPE
            SYNTAX                     Counter32
            MAX-ACCESS                 read-only
            STATUS                     current
            DESCRIPTION                "."
            ::= { zfsARCStatsEntry 13 }

          zfsARCL2Hits                 OBJECT-TYPE
            SYNTAX                     Counter32
            MAX-ACCESS                 read-only
            STATUS                     current
            DESCRIPTION                "."
            ::= { zfsARCStatsEntry 14 }

          zfsARCL2Misses               OBJECT-TYPE
            SYNTAX                     Counter32
            MAX-ACCESS                 read-only
            STATUS                     current
            DESCRIPTION                "."
            ::= { zfsARCStatsEntry 15 }
-- }}}

      -- {{{ .1.3.6.1.4.1.8767.2.6.8 zfsVFSIOPSTable
      zfsVFSIOPSTable                  OBJECT-TYPE
        SYNTAX                         SEQUENCE OF ZFSVFSIOPSEntry
        MAX-ACCESS                     not-accessible
        STATUS                         current
        DESCRIPTION                    "A list of ZFS VFS IOPS status information.
                                        This table contains additional objects for
                                        the zfsPoolStatusTable."
        ::= { zfsStats 8 }

        zfsVFSIOPSEntry                OBJECT-TYPE
          SYNTAX                       ZFSVFSIOPSEntry
          MAX-ACCESS                   not-accessible
          STATUS                       current
          DESCRIPTION                  "An entry containing ZFS ARC status values."
          AUGMENTS                     { zfsPoolStatusEntry }
          ::= { zfsVFSIOPSTable 1 }

          ZFSVFSIOPSEntry             ::= SEQUENCE {
            zfsVFSIOPSIndex           CounterIndex,

            zfsOperReads              Counter32,
            zfsOperWrites             Counter32
          }

          zfsVFSIOPSIndex             OBJECT-TYPE
            SYNTAX                     CounterIndex
            MAX-ACCESS                 not-accessible
            STATUS                     current
            DESCRIPTION                "Reference Index for each counter."
            ::= { zfsVFSIOPSEntry 1 }

          zfsOperReads                 OBJECT-TYPE
            SYNTAX                     Counter32
            MAX-ACCESS                 read-only
            STATUS                     current
            DESCRIPTION                "."
            ::= { zfsVFSIOPSEntry 3 }

          zfsOperWrites                OBJECT-TYPE
            SYNTAX                     Counter32
            MAX-ACCESS                 read-only
            STATUS                     current
            DESCRIPTION                "."
            ::= { zfsVFSIOPSEntry 4 }
-- }}}

      -- {{{ .1.3.6.1.4.1.8767.2.6.9 zfsVFSThroughputTable
      zfsVFSThroughputTable            OBJECT-TYPE
        SYNTAX                         SEQUENCE OF ZFSVFSThroughputEntry
        MAX-ACCESS                     not-accessible
        STATUS                         current
        DESCRIPTION                    "A list of ZFS VFS Throughput status information.
                                        This table contains additional objects for
                                        the zfsPoolStatusTable."
        ::= { zfsStats 9 }

        zfsVFSThroughputEntry          OBJECT-TYPE
          SYNTAX                       ZFSVFSThroughputEntry
          MAX-ACCESS                   not-accessible
          STATUS                       current
          DESCRIPTION                  "An entry containing ZFS ARC status values."
          AUGMENTS                     { zfsPoolStatusEntry }
          ::= { zfsVFSThroughputTable 1 }

          ZFSVFSThroughputEntry        ::= SEQUENCE {
            zfsVFSThroughputIndex      CounterIndex,

            zfsBandwidthReads          Counter32,
            zfsBandwidthWrites         Counter32
          }

          zfsVFSThroughputIndex        OBJECT-TYPE
            SYNTAX                     CounterIndex
            MAX-ACCESS                 not-accessible
            STATUS                     current
            DESCRIPTION                "Reference Index for each counter."
            ::= { zfsVFSThroughputEntry 1 }

          zfsBandwidthReads            OBJECT-TYPE
            SYNTAX                     Counter32
            MAX-ACCESS                 read-only
            STATUS                     current
            DESCRIPTION                "."
            ::= { zfsVFSThroughputEntry 3 }

          zfsBandwidthWrites           OBJECT-TYPE
            SYNTAX                     Counter32
            MAX-ACCESS                 read-only
            STATUS                     current
            DESCRIPTION                "."
            ::= { zfsVFSThroughputEntry 4 }
-- }}}

      -- {{{ .1.3.6.1.4.1.8767.2.6.10 zfsZILStatsTable
      zfsZILStatsTable                 OBJECT-TYPE
        SYNTAX                         SEQUENCE OF ZFSZILStatsEntry
        MAX-ACCESS                     not-accessible
        STATUS                         current
        DESCRIPTION                    "A list of ZFS ZIL status information."
        ::= { zfsStats 10 }

        zfsZILStatsEntry               OBJECT-TYPE
          SYNTAX                       ZFSZILStatsEntry
          MAX-ACCESS                   not-accessible
          STATUS                       current
          DESCRIPTION                  "An entry containing ZFS ZIL status values."
          INDEX                        { zfsZILStatsIndex }
          ::= { zfsZILStatsTable 1 }

          ZFSZILStatsEntry             ::= SEQUENCE {
            zfsZILStatsIndex           CounterIndex,

            zfsZILCommitCnt            Counter32,
            zfsZILCommitWriterCnt      Counter32,
            zfsZILITXCnt               Counter32,
            zfsZILITXIndirectCnt       Counter32,
            zfsZILITXIndirectBytes     Counter32,
            zfsZILITXCopiedCnt         Counter32,
            zfsZILITXCopiedBytes       Counter32,
            zfsZILITXNeedcopyCnt       Counter32,
            zfsZILITXNeedcopyBytes     Counter32,
            zfsZILITXMetaslabNormalCnt Counter32,
            zfsZILITXMetaslabNormalBytes Counter32,
            zfsZILITXMetaslabSLOGCnt   Counter32,
            zfsZILITXMetaslabSLOGBytes Counter32
          }

          zfsZILStatsIndex             OBJECT-TYPE
            SYNTAX                     CounterIndex
            MAX-ACCESS                 not-accessible
            STATUS                     current
            DESCRIPTION                "Reference Index for each counter."
            ::= { zfsZILStatsEntry 1 }

          zfsZILCommitCnt              OBJECT-TYPE
            SYNTAX                     Counter32
            MAX-ACCESS                 read-only
            STATUS                     current
            DESCRIPTION                "."
            ::= { zfsZILStatsEntry 2 }

          zfsZILCommitWriterCnt        OBJECT-TYPE
            SYNTAX                     Counter32
            MAX-ACCESS                 read-only
            STATUS                     current
            DESCRIPTION                "."
            ::= { zfsZILStatsEntry 3 }

          zfsZILITXCnt                 OBJECT-TYPE
            SYNTAX                     Counter32
            MAX-ACCESS                 read-only
            STATUS                     current
            DESCRIPTION                "."
            ::= { zfsZILStatsEntry 4 }

          zfsZILITXIndirectCnt         OBJECT-TYPE
            SYNTAX                     Counter32
            MAX-ACCESS                 read-only
            STATUS                     current
            DESCRIPTION                "."
            ::= { zfsZILStatsEntry 5 }

          zfsZILITXIndirectBytes       OBJECT-TYPE
            SYNTAX                     Counter32
            MAX-ACCESS                 read-only
            STATUS                     current
            DESCRIPTION                "."
            ::= { zfsZILStatsEntry 6 }

          zfsZILITXCopiedCnt           OBJECT-TYPE
            SYNTAX                     Counter32
            MAX-ACCESS                 read-only
            STATUS                     current
            DESCRIPTION                "."
            ::= { zfsZILStatsEntry 7 }

          zfsZILITXCopiedBytes         OBJECT-TYPE
            SYNTAX                     Counter32
            MAX-ACCESS                 read-only
            STATUS                     current
            DESCRIPTION                "."
            ::= { zfsZILStatsEntry 8 }

          zfsZILITXNeedcopyCnt         OBJECT-TYPE
            SYNTAX                     Counter32
            MAX-ACCESS                 read-only
            STATUS                     current
            DESCRIPTION                "."
            ::= { zfsZILStatsEntry 9 }

          zfsZILITXNeedcopyBytes       OBJECT-TYPE
            SYNTAX                     Counter32
            MAX-ACCESS                 read-only
            STATUS                     current
            DESCRIPTION                "."
            ::= { zfsZILStatsEntry 10 }

          zfsZILITXMetaslabNormalCnt   OBJECT-TYPE
            SYNTAX                     Counter32
            MAX-ACCESS                 read-only
            STATUS                     current
            DESCRIPTION                "."
            ::= { zfsZILStatsEntry 11 }

          zfsZILITXMetaslabNormalBytes OBJECT-TYPE
            SYNTAX                     Counter32
            MAX-ACCESS                 read-only
            STATUS                     current
            DESCRIPTION                "."
            ::= { zfsZILStatsEntry 12 }

          zfsZILITXMetaslabSLOGCnt     OBJECT-TYPE
            SYNTAX                     Counter32
            MAX-ACCESS                 read-only
            STATUS                     current
            DESCRIPTION                "."
            ::= { zfsZILStatsEntry 13 }

          zfsZILITXMetaslabSLOGBytes   OBJECT-TYPE
            SYNTAX                     Counter32
            MAX-ACCESS                 read-only
            STATUS                     current
            DESCRIPTION                "."
            ::= { zfsZILStatsEntry 14 }
-- }}}

      -- {{{ .1.3.6.1.4.1.8767.2.6.11 zfsPoolDevStatsTable
      zfsPoolDevStatusTable            OBJECT-TYPE
        SYNTAX                         SEQUENCE OF ZFSPoolDevStatusEntry
        MAX-ACCESS                     not-accessible
        STATUS                         current
        DESCRIPTION                    "A list of ZFS pool device status information."
        ::= { zfsStats 11 }

        zfsPoolDevStatusEntry          OBJECT-TYPE
          SYNTAX                       ZFSPoolDevStatusEntry
          MAX-ACCESS                   not-accessible
          STATUS                       current
          DESCRIPTION                  "An entry containing ZFS pool device status values."
          INDEX                        { zfsPoolDevStatusIndex }
          ::= { zfsPoolDevStatusTable 1 }

          ZFSPoolDevStatusEntry        ::= SEQUENCE {
            zfsPoolDevStatusIndex      CounterIndex,

            zfsPoolDevName             DisplayString,
            zfsPoolDevState            ZFSPoolStatusValue,
            zfsPoolDevRead             Integer32,
            zfsPoolDevWrite            Integer32,
            zfsPoolDevCksum            Integer32
          }

          zfsPoolDevStatusIndex        OBJECT-TYPE
            SYNTAX                     CounterIndex
            MAX-ACCESS                 not-accessible
            STATUS                     current
            DESCRIPTION                "Reference Index for each counter."
            ::= { zfsPoolDevStatusEntry 1 }

          zfsPoolDevName               OBJECT-TYPE
            SYNTAX                     DisplayString
            MAX-ACCESS                 read-only
            STATUS                     current
            DESCRIPTION                "Name of ZFS pool device."
            ::= { zfsPoolDevStatusEntry 2 }

          zfsPoolDevState              OBJECT-TYPE
            SYNTAX                     ZFSPoolStatusValue
            MAX-ACCESS                 read-only
            STATUS                     current
            DESCRIPTION                "Status of ZFS pool device."
            ::= { zfsPoolDevStatusEntry 3 }

          zfsPoolDevRead               OBJECT-TYPE
            SYNTAX                     Integer32
            MAX-ACCESS                 read-only
            STATUS                     current
            DESCRIPTION                "Number of read errors on ZFS pool device."
            ::= { zfsPoolDevStatusEntry 4 }

          zfsPoolDevWrite              OBJECT-TYPE
            SYNTAX                     Integer32
            MAX-ACCESS                 read-only
            STATUS                     current
            DESCRIPTION                "Number of write errors on ZFS pool device."
            ::= { zfsPoolDevStatusEntry 5 }

          zfsPoolDevCksum              OBJECT-TYPE
            SYNTAX                     Integer32
            MAX-ACCESS                 read-only
            STATUS                     current
            DESCRIPTION                "Number of cksum errors on ZFS pool device."
            ::= { zfsPoolDevStatusEntry 6 }
-- }}}

      -- {{{ .1.3.6.1.4.1.8767.2.6.12 zfsDufsStatsTable
      zfsDbufStatsTable                OBJECT-TYPE
        SYNTAX                         SEQUENCE OF ZFSDbufStatsEntry
        MAX-ACCESS                     not-accessible
        STATUS                         current
        DESCRIPTION                    "A list of ZFS dbuf status information."
        ::= { zfsStats 12 }

        zfsDbufStatsEntry              OBJECT-TYPE
          SYNTAX                       ZFSDbufStatsEntry
          MAX-ACCESS                   not-accessible
          STATUS                       current
          DESCRIPTION                  "An entry containing ZFS dbuf status values."
          INDEX                        { zfsDbufStatsIndex }
          ::= { zfsDbufStatsTable 1 }

          ZFSDbufStatsEntry            ::= SEQUENCE {
            zfsDbufStatsIndex          CounterIndex,

            zfsDbufPoolName            DisplayString,
            zfsDbufObjSet              Integer32,
            zfsDbufObject              Integer32,
            zfsDbufLevel               Integer32,
            zfsDbufBlkId               Integer32,
            zfsDbufOffset              Integer32,
            zfsDbufDBSize              Integer32,
            zfsDbufMeta                Integer32,
            zfsDbufState               ZFSPoolStatusValue,
            zfsDbufDBHolds             Integer32,
            zfsDbufList                Integer32,
            zfsDbufAType               Integer32,
            zfsDbufIndex               Integer32,
            zfsDbufFlags               DisplayString,
            zfsDbufCount               Integer32,
            zfsDbufASize               Integer32,
            zfsDbufAccess              Integer32,
            zfsDbufMRU                 Integer32,
            zfsDbufGMRU                Integer32,
            zfsDbufMFU                 Integer32,
            zfsDbufGMFU                Integer32,
            zfsDbufL2                  Integer32,
            zfsDbufL2DAttr             Integer32,
            zfsDbufL2ASize             Integer32,
            zfsDbufL2Comp              ZFSDbufL2CompValue,
            zfsDbufAHolds              Integer32,
            zfsDbufDType               ZFSDbufTypeValue,
            zfsDbufBType               ZFSDbufTypeValue,
            zfsDbufDataBS              Integer32,
            zfsDbufMetaBS              Integer32,
            zfsDbufBSize               Integer32,
            zfsDbufLvls                Integer32,
            zfsDbufDHolds              Integer32,
            zfsDbufBlocks              Integer32,
            zfsDbufDSize               Integer32
          }

          zfsDbufStatsIndex            OBJECT-TYPE
            SYNTAX                     CounterIndex
            MAX-ACCESS                 not-accessible
            STATUS                     current
            DESCRIPTION                "Reference Index for each counter."
            ::= { zfsDbufStatsEntry 1 }

          zfsDbufPoolName              OBJECT-TYPE
            SYNTAX                     DisplayString
            MAX-ACCESS                 read-only
            STATUS                     current
            DESCRIPTION                "Name of ZFS pool."
            ::= { zfsDbufStatsEntry 2 }

          zfsDbufObjSet                OBJECT-TYPE
            SYNTAX                     Integer32
            MAX-ACCESS                 read-only
            STATUS                     current
            DESCRIPTION                "."
            ::= { zfsDbufStatsEntry 3 }

          zfsDbufObject                OBJECT-TYPE
            SYNTAX                     Integer32
            MAX-ACCESS                 read-only
            STATUS                     current
            DESCRIPTION                "."
            ::= { zfsDbufStatsEntry 4 }

          zfsDbufLevel                 OBJECT-TYPE
            SYNTAX                     Integer32
            MAX-ACCESS                 read-only
            STATUS                     current
            DESCRIPTION                "."
            ::= { zfsDbufStatsEntry 5 }

          zfsDbufBlkId                 OBJECT-TYPE
            SYNTAX                     Integer32
            MAX-ACCESS                 read-only
            STATUS                     current
            DESCRIPTION                "."
            ::= { zfsDbufStatsEntry 6 }

          zfsDbufOffset                OBJECT-TYPE
            SYNTAX                     Integer32
            MAX-ACCESS                 read-only
            STATUS                     current
            DESCRIPTION                "."
            ::= { zfsDbufStatsEntry 7 }

          zfsDbufDBSize                OBJECT-TYPE
            SYNTAX                     Integer32
            MAX-ACCESS                 read-only
            STATUS                     current
            DESCRIPTION                "."
            ::= { zfsDbufStatsEntry 8 }

          zfsDbufMeta                  OBJECT-TYPE
            SYNTAX                     Integer32
            MAX-ACCESS                 read-only
            STATUS                     current
            DESCRIPTION                "."
            ::= { zfsDbufStatsEntry 9 }

          zfsDbufState                 OBJECT-TYPE
            SYNTAX                     ZFSPoolStatusValue
            MAX-ACCESS                 read-only
            STATUS                     current
            DESCRIPTION                "."
            ::= { zfsDbufStatsEntry 10 }

          zfsDbufDBHolds               OBJECT-TYPE
            SYNTAX                     Integer32
            MAX-ACCESS                 read-only
            STATUS                     current
            DESCRIPTION                "."
            ::= { zfsDbufStatsEntry 11 }

          zfsDbufList                  OBJECT-TYPE
            SYNTAX                     Integer32
            MAX-ACCESS                 read-only
            STATUS                     current
            DESCRIPTION                "."
            ::= { zfsDbufStatsEntry 12 }

          zfsDbufAType                 OBJECT-TYPE
            SYNTAX                     Integer32
            MAX-ACCESS                 read-only
            STATUS                     current
            DESCRIPTION                "."
            ::= { zfsDbufStatsEntry 13 }

          zfsDbufIndex                 OBJECT-TYPE
            SYNTAX                     Integer32
            MAX-ACCESS                 read-only
            STATUS                     current
            DESCRIPTION                "."
            ::= { zfsDbufStatsEntry 14 }

          zfsDbufFlags                 OBJECT-TYPE
            SYNTAX                     DisplayString
            MAX-ACCESS                 read-only
            STATUS                     current
            DESCRIPTION                "."
            ::= { zfsDbufStatsEntry 15 }

          zfsDbufCount                 OBJECT-TYPE
            SYNTAX                     Integer32
            MAX-ACCESS                 read-only
            STATUS                     current
            DESCRIPTION                "."
            ::= { zfsDbufStatsEntry 16 }

          zfsDbufASize                 OBJECT-TYPE
            SYNTAX                     Integer32
            MAX-ACCESS                 read-only
            STATUS                     current
            DESCRIPTION                "."
            ::= { zfsDbufStatsEntry 17 }

          zfsDbufAccess                OBJECT-TYPE
            SYNTAX                     Integer32
            MAX-ACCESS                 read-only
            STATUS                     current
            DESCRIPTION                "."
            ::= { zfsDbufStatsEntry 18 }

          zfsDbufMRU                   OBJECT-TYPE
            SYNTAX                     Integer32
            MAX-ACCESS                 read-only
            STATUS                     current
            DESCRIPTION                "."
            ::= { zfsDbufStatsEntry 19 }

          zfsDbufGMRU                  OBJECT-TYPE
            SYNTAX                     Integer32
            MAX-ACCESS                 read-only
            STATUS                     current
            DESCRIPTION                "."
            ::= { zfsDbufStatsEntry 20 }

          zfsDbufMFU                   OBJECT-TYPE
            SYNTAX                     Integer32
            MAX-ACCESS                 read-only
            STATUS                     current
            DESCRIPTION                "."
            ::= { zfsDbufStatsEntry 21 }

          zfsDbufGMFU                  OBJECT-TYPE
            SYNTAX                     Integer32
            MAX-ACCESS                 read-only
            STATUS                     current
            DESCRIPTION                "."
            ::= { zfsDbufStatsEntry 22 }

          zfsDbufL2                    OBJECT-TYPE
            SYNTAX                     Integer32
            MAX-ACCESS                 read-only
            STATUS                     current
            DESCRIPTION                "."
            ::= { zfsDbufStatsEntry 23 }

          zfsDbufL2DAttr               OBJECT-TYPE
            SYNTAX                     Integer32
            MAX-ACCESS                 read-only
            STATUS                     current
            DESCRIPTION                "."
            ::= { zfsDbufStatsEntry 24 }

          zfsDbufL2ASize               OBJECT-TYPE
            SYNTAX                     Integer32
            MAX-ACCESS                 read-only
            STATUS                     current
            DESCRIPTION                "."
            ::= { zfsDbufStatsEntry 25 }

          zfsDbufL2Comp                OBJECT-TYPE
            SYNTAX                     ZFSDbufL2CompValue
            MAX-ACCESS                 read-only
            STATUS                     current
            DESCRIPTION                "."
            ::= { zfsDbufStatsEntry 26 }

          zfsDbufAHolds                OBJECT-TYPE
            SYNTAX                     Integer32
            MAX-ACCESS                 read-only
            STATUS                     current
            DESCRIPTION                "."
            ::= { zfsDbufStatsEntry 27 }

          zfsDbufDType                 OBJECT-TYPE
            SYNTAX                     ZFSDbufTypeValue
            MAX-ACCESS                 read-only
            STATUS                     current
            DESCRIPTION                "."
            ::= { zfsDbufStatsEntry 28 }

          zfsDbufBType                 OBJECT-TYPE
            SYNTAX                     ZFSDbufTypeValue
            MAX-ACCESS                 read-only
            STATUS                     current
            DESCRIPTION                "."
            ::= { zfsDbufStatsEntry 29 }

          zfsDbufDataBS                OBJECT-TYPE
            SYNTAX                     Integer32
            MAX-ACCESS                 read-only
            STATUS                     current
            DESCRIPTION                "."
            ::= { zfsDbufStatsEntry 30 }

          zfsDbufMetaBS                OBJECT-TYPE
            SYNTAX                     Integer32
            MAX-ACCESS                 read-only
            STATUS                     current
            DESCRIPTION                "."
            ::= { zfsDbufStatsEntry 31 }

          zfsDbufBSize                 OBJECT-TYPE
            SYNTAX                     Integer32
            MAX-ACCESS                 read-only
            STATUS                     current
            DESCRIPTION                "."
            ::= { zfsDbufStatsEntry 32 }

          zfsDbufLvls                  OBJECT-TYPE
            SYNTAX                     Integer32
            MAX-ACCESS                 read-only
            STATUS                     current
            DESCRIPTION                "."
            ::= { zfsDbufStatsEntry 33 }

          zfsDbufDHolds                OBJECT-TYPE
            SYNTAX                     Integer32
            MAX-ACCESS                 read-only
            STATUS                     current
            DESCRIPTION                "."
            ::= { zfsDbufStatsEntry 34 }

          zfsDbufBlocks                OBJECT-TYPE
            SYNTAX                     Integer32
            MAX-ACCESS                 read-only
            STATUS                     current
            DESCRIPTION                "."
            ::= { zfsDbufStatsEntry 35 }

          zfsDbufDSize                 OBJECT-TYPE
            SYNTAX                     Integer32
            MAX-ACCESS                 read-only
            STATUS                     current
            DESCRIPTION                "."
            ::= { zfsDbufStatsEntry 36 }
-- }}}
-- }}}
END

-- Local variables:
-- mode: text
-- mode: folding
-- mode: font-lock
-- indent-tabs-mode: nil
